(setq r_nomal nil r_alin nil r_ras nil r_lperft nil r_lpersa nil r_lprvados nil
      r_lprpuentes nil r_lprI&R nil r_lprnorep nil r_lprtraza nil r_lrpvados nil
      r_lbei nil r_lbii nil r_lbid nil r_lbed nil r_lpeje nil
)

(defun |R|TITG (r_nomal)
	(list
		(list (strcase r_nomal))
		(list "")
		(list "PLANILLA DE REPLANTEO DE LA TRAZA")
		(list "")
	)
)
(defun |R|TITCS ()
	(list
		(list "")
		(list "Calzada")
		(list nil "Borde Izquierdo" "" "" "Eje" "" "" "Borde Derecho")
		(list "Progresiva" "Norte" "Este" "Elev" "Norte" "Este" "Elev" "Norte" "Este" "Elev" "Características")
	)
)
(defun |R|TITCD ()
	(list
		(list "")
		(list nil "Calzada Izquierda" "" "" "" "" "" "Calzada Derecha")
		(list nil "Borde Externo" "" "" "Borde Interno" "" "" "Borde Interno" "" "" "Borde Externo")
		(list "Progresiva" "Norte" "Este" "Elev" "Norte" "Este" "Elev" "Norte" "Este" "Elev" "Norte" "Este" "Elev" "Características")
	)
)
(defun |R|CARACT ()
	(list
		(list "")
		(list "CODIGOS DE CARACTERISTICAS")
		(list "PL*" "Punto de Línea")
		(list "TE*" "Tangente Espiral")
		(list "EC*" "Espiral Circular")
		(list "CC*" "Punto Medio Curva Circular")
		(list "CE*" "Circular Espiral")
		(list "ET*" "Espiral Tangente")
		(list "PC*" "Principo de Curva")
		(list "FC*" "Fin de Curva")
		(list "V*" "Vértice Planimétrico")
		(list "PIV" "Vértice Altimétrico")
		(list "PCV" "Principio de Curva Vertical")
		(list "FCV" "Fin de Curva Vertical")
		(list "VP" "Punto de variación de Peralte")
		(list "I+" "Inicio del Evento")
		(list "F+" "Fin del Evento")
		(list "PT" "Perfil Tipo")
	)
)

;obtener los datos del bloque de perfil tipo
(defun |R|OBTDPT (r_nbpt)
	(defun |R|OBTDPE (r_ent)
		(setq r_lppe (|A|LISVER r_ent) r_pp (car r_lppe) r_sp (cadr r_lppe) r_up (last r_lppe) r_dx (|K|DX r_pp r_up) r_dy (|K|DY r_sp r_pp))
		(list r_dx r_dy)
	)
	(setq r_lisent (cadr (|B|LISTENT r_nbpt)) r_aci nil r_acd nil r_lcalz '() r_lbase '() r_lsubb '())
	(foreach r_lent r_lisent
		(setq r_tent (|O|ITEM 8 r_lent))
		(cond
			((wcmatch r_tent "*Calzada") (setq r_lcalz (cons (|R|OBTDPE r_lent) r_lcalz)))
			((wcmatch r_tent "*SubBase") (setq r_lsubb (cons (|R|OBTDPE r_lent) r_lsubb)))
			((wcmatch r_tent "*Base") (setq r_lbase (cons (|R|OBTDPE r_lent) r_lbase)))
		)
	)
	(list (|L|ORDENAR r_lcalz) (|L|ORDENAR r_lbase) (|L|ORDENAR r_lsubb))
)

;determinar si una progresiva corresponde a un area no replanteada
(defun |R|ENNOREP (r_pr r_lprnorep)
	(cond
		((null r_lprnorep) nil)
		((|N|ENTREE r_pr (|L|SUBL (car r_lprnorep) 2))
			T
		)
		(T (|R|ENNOREP r_pr (cdr r_lprnorep)))
	)
)

;determinar si una progresiva cae en el ámbito de adecuación a un vado o badén
(defun |R|ENVADO (r_pr r_lprv)
	(cond
		((null r_lprv) nil)
		((|N|ENTRE r_pr (|L|SUBL (car r_lprv) 2))
			(car r_lprv)
		)
		(T (|R|ENVADO r_pr (cdr r_lprv)))
	)
)

;procesar las transiciones de peralte en el ámbito de adecuación de un vado o badén
(defun |R|PROCVADO (r_dpr r_dvado)
	(setq r_pr (car r_dpr) r_tip (cadr r_dpr) r_pritp (car r_dvado) r_prftp (cadr r_dvado) r_prmv (caddr r_dvado)
	      r_lvh (cadddr r_dvado) r_sesc (nth 4 r_dvado) r_tipv (last r_dvado)
	      r_lpe (|A|PINS r_pr r_alin) r_pe (car r_lpe) r_dir (cadr r_lpe) r_cras (|P|ELEV r_pr r_ras)
	      r_pt (cdr (|A|CALCVAL r_lperft r_pr)) r_sc (car r_pt) r_ac (cadr r_pt) r_flecha (/ (caddr r_pt) -100) r_nbl (last r_pt)
	      r_lpsa (|A|CALCVAL r_lpersa r_pr) r_sai (caddr r_lpsa) r_sad (last r_lpsa)
	      r_lpsai (|A|CALCVAL r_lpersa r_pritp) r_perii (/ (car r_lpsai) 100) r_perdi (/ (cadr r_lpsai) 100)
	      r_saii (caddr r_lpsai) r_sadi (last r_lpsai) r_priv (- r_prmv (/ r_lvh 2)) r_prfv (+ r_prmv (/ r_lvh 2))
	      r_lpsaf (|A|CALCVAL r_lpersa r_prftp) r_perif (/ (car r_lpsaf) 100) r_perdf (/ (cadr r_lpsaf) 100)
	      r_saif (caddr r_lpsaf) r_sadf (last r_lpsaf) 
	)
	(if (eq r_sesc "I") (setq r_perim -0.01 r_perdm 0.01) (setq r_perim 0.01 r_perdm -0.01))
	(cond
		((|N|ENTRE r_pr (list r_pritp r_priv))
			(setq r_peri (cadr (|L|INTERP (list r_pritp r_perii) (list r_priv r_perim) r_pr r_pritp r_priv))
			      r_perd (cadr (|L|INTERP (list r_pritp r_perdi) (list r_priv r_perdm) r_pr r_pritp r_priv))
			)
		)
		((|N|ENTRE r_pr (list r_prfv r_prftp))
			(setq r_peri (cadr (|L|INTERP (list r_prfv r_perim) (list r_prftp r_perif) r_pr r_prfv r_prftp))
			      r_perd (cadr (|L|INTERP (list r_prfv r_perim) (list r_prftp r_perdf) r_pr r_prfv r_prftp))
			)
		)
		(T
			(setq r_peri r_perim r_perd r_perdm r_cras (- r_cras 0.02))
			(if (eq r_tipv "V") (setq r_sai 3.0 r_sad 3.0) (setq r_sai 0.0 r_sad 0.0))
		)
	)
	(|R|REPS r_pr r_cras r_pe r_dir r_nbl r_sai r_sad r_peri r_perd r_tip)
)

;porcesar los puntos singulares de un vado o badén
(defun |R|PPSVADO (r_lprv)
	(cond
		((null r_lprv) nil)
		(T
			(setq r_dvado (car r_lprv) r_prmv (caddr r_dvado) r_lvh (cadddr r_dvado) r_sesc (nth 4 r_dvado) r_tipv (last r_dvado)
			      r_pt (cdr (|A|CALCVAL r_lperft r_prmv)) r_sc (car r_pt) r_ac (cadr r_pt) r_flecha (/ (caddr r_pt) -100) r_nbl (last r_pt)
			      r_priv (- r_prmv (/ r_lvh 2)) r_peri (if (eq r_sesc "I") -0.01 0.01) r_perd (if (eq r_sesc "I") 0.01 -0.01)
			      r_sa (if (eq r_tipv "V") 3.0 0.0) r_sai r_sa r_sad r_sa
			      r_cras (|P|ELEV r_priv r_ras) r_lpe (|A|PINS r_priv r_alin) r_pe (car r_lpe) r_dir (cadr r_lpe)
			      r_lptriv (|R|REPS r_priv (- r_cras 0.02) r_pe r_dir r_nbl r_sai r_sad r_peri r_perd (strcat "I" r_tipv))
			      r_prfp (+ r_priv 0.05) r_cras (|P|ELEV r_prfp r_ras) r_lpe (|A|PINS r_prfp r_alin) r_pe (car r_lpe) r_dir (cadr r_lpe)
			      r_lptrfp (|R|REPS r_prfp r_cras r_pe r_dir r_nbl 0.0 0.0 r_peri r_perd "F+Pav")
			      r_lpe (|A|PINS r_prmv r_alin) r_pe (car r_lpe) r_dir (cadr r_lpe) r_cras (|P|ELEV r_prmv r_ras)
			      r_lptrmv (|R|REPS r_prmv (- r_cras 0.02) r_pe r_dir r_nbl r_sai r_sad r_peri r_perd "")
			      r_prfv (+ r_prmv (/ r_lvh 2)) r_cras (|P|ELEV r_prfv r_ras) r_lpe (|A|PINS r_prfv r_alin) r_pe (car r_lpe) r_dir (cadr r_lpe)
			      r_lptrfv (|R|REPS r_prfv (- r_cras 0.02) r_pe r_dir r_nbl r_sai r_sad r_peri r_perd (strcat "F" r_tipv))
			      r_prip (- r_prfv 0.05) r_cras (|P|ELEV r_prip r_ras) r_lpe (|A|PINS r_prip r_alin) r_pe (car r_lpe) r_dir (cadr r_lpe)
			      r_lptrip (|R|REPS r_prip r_cras r_pe r_dir r_nbl 0.0 0.0 r_peri r_perd "I+Pav")
			)
			(append (list r_lptriv r_lptrfp r_lptrmv r_lptrip r_lptrfv) (|R|PPSVADO (cdr r_lprv)))
  		)
	)
)

;poner un punto de replanteo
(defun |R|PPR (r_pto r_prg r_cota r_cod)
	(|B|INSERT "PTO" r_pto "R_Replanteo" r_dir 0.25 (list (rtos r_prg 2 2) (rtos r_cota 2 2) r_cod))
)

;calcular los puntos de replanteo para un perfil de calzadas indivisas
(defun |R|REPS (r_pr r_cras r_pe r_dir r_nbl r_sai r_sad r_peri r_perde r_tip)
	(setq r_ldpt (|R|OBTDPT r_nbl) r_ldc (car r_ldpt) r_ldb (cadr r_ldpt) r_ldsb (caddr r_ldpt)
	      r_aci (abs (caar r_ldc)) r_eci (cadar r_ldc) r_acd (caadr r_ldc) r_ecd (cadadr r_ldc)
	      r_abi (abs (caar r_ldb)) r_ebi (cadar r_ldb) r_abd (caadr r_ldb) r_ebd (cadadr r_ldb)
      	      r_asi (abs (caar r_ldsb)) r_esi (cadar r_ldsb) r_asd (caadr r_ldsb) r_esd (cadadr r_ldsb)
	      r_acis (+ r_aci r_sai) r_pbi (|K|POLAR r_pe (+ r_dir (/ PI 2)) r_acis) r_cbi (+ r_cras (* r_acis r_peri))
	      r_acds (+ r_acd r_sad) r_pbd (|K|POLAR r_pe (- r_dir (/ PI 2)) r_acds) r_cbd (+ r_cras (* r_acds r_perd))
	      r_cbas (- r_cras r_eci)
	      r_abis (+ r_abi r_sai) r_pbai (|K|POLAR r_pe (+ r_dir (/ PI 2)) r_abis) r_cbai (+ r_cbas (* r_abis r_peri))
	      r_abds (+ r_abd r_sad) r_pbad (|K|POLAR r_pe (- r_dir (/ PI 2)) r_abds) r_cbad (+ r_cbas (* r_abds r_perd))
	      r_csbas (- r_cbas r_ebi)
	      r_asis (+ r_asi r_sai) r_psbi (|K|POLAR r_pe (+ r_dir (/ PI 2)) r_asis) r_csbi (+ r_csbas (* r_asis r_peri))
	      r_asds (+ r_asd r_sad) r_psbd (|K|POLAR r_pe (- r_dir (/ PI 2)) r_asds) r_csbd (+ r_csbas (* r_asds r_perd))
	      r_csras (- r_csbas r_esi) r_csri (- r_csbi r_esi) r_csrd (- r_csbd r_esi)
	      r_lbei (cons (list r_pr (|K|Z+ r_pbi r_cbi)) r_lbei) r_lbii (cons (list r_pr (|K|Z+ r_pe r_cras)) r_lbii)
	      r_lbid (cons (list r_pr (|K|Z+ r_pe r_cras)) r_lbid) r_lbed (cons (list r_pr (|K|Z+ r_pbd r_cbd)) r_lbed)
	      r_lpeje (cons (list r_pr (|K|Z+ r_pe r_cras)) r_lpeje)
	)
;;;	(|R|PPR r_pe r_pr r_cras "EJE")
;;;	(|R|PPR r_pbi r_pr r_cbi "BI")
;;;	(|R|PPR r_pbd r_pr r_cbd "BD")
	(list
		(list r_pr (|K|PTATOP (|K|Z+ r_psbi r_csri)) (|K|PTATOP (|K|Z+ r_pe r_csras)) (|K|PTATOP (|K|Z+ r_psbd r_csrd)) r_tip) 
		(list r_pr (|K|PTATOP (|K|Z+ r_psbi r_csbi)) (|K|PTATOP (|K|Z+ r_pe r_csbas)) (|K|PTATOP (|K|Z+ r_psbd r_csbd)) r_tip) 
		(list r_pr (|K|PTATOP (|K|Z+ r_pbai r_cbai)) (|K|PTATOP (|K|Z+ r_pe r_cbas)) (|K|PTATOP (|K|Z+ r_pbad r_cbad)) r_tip) 
		(list r_pr (|K|PTATOP (|K|Z+ r_pbi r_cbi)) (|K|PTATOP (|K|Z+ r_pe r_cras)) (|K|PTATOP (|K|Z+ r_pbd r_cbd)) r_tip)
	)
)

;calcular los puntos de replanteo para un perfil de calzadas con separación central
(defun |R|REPD (r_pr r_cras r_pe r_dir r_sc r_nbl r_sai r_sad r_peri r_perde r_tip)
	(setq r_ldpt (|R|OBTDPT r_nbl) r_ldc (car r_ldpt) r_ldb (cadr r_ldpt) r_ldsb (caddr r_ldpt)
	      r_aci (abs (caar r_ldc)) r_eci (cadar r_ldc) r_acd (caadr r_ldc) r_ecd (cadadr r_ldc)
	      r_abi (abs (caar r_ldb)) r_ebi (cadar r_ldb) r_abd (caadr r_ldb) r_ebd (cadadr r_ldb)
      	      r_asi (abs (caar r_ldsb)) r_esi (cadar r_ldsb) r_asd (caadr r_ldsb) r_esd (cadadr r_ldsb)
	      r_pbii (|K|POLAR r_pe (+ r_dir (/ PI 2)) r_sc) r_acis (+ r_aci r_sai)
	      r_pbei (|K|POLAR r_pbii (+ r_dir (/ PI 2)) r_acis) r_cbei (+ r_cras (* r_acis r_peri))
	      r_pbid (|K|POLAR r_pe (- r_dir (/ PI 2)) r_sc) r_acds (+ r_acd r_sad)
	      r_pbed (|K|POLAR r_pbid (- r_dir (/ PI 2)) r_acds) r_cbed (+ r_cras (* r_acds r_perd))
	      r_lbei (cons (list r_pr (|K|Z+ r_pbei r_cbei)) r_lbei) r_lbii (cons (list r_pr (|K|Z+ r_pbii r_cras)) r_lbii)
	      r_lbid (cons (list r_pr (|K|Z+ r_pid r_cras)) r_lbid) r_lbed (cons (list r_pr (|K|Z+ r_pbed r_cbed)) r_lbed)
	      r_lpeje (cons (list r_pr (|K|Z+ r_pe r_cras)) r_lpeje)
	)
;;;	(|R|PPR r_pbii r_pr r_cras "BII") (|R|PPR r_pbei r_pr r_cbei "BEI")
;;;	(|R|PPR r_pbid r_pr r_cras "BID") (|R|PPR r_pbed r_pr r_cbed "BED")
	(list r_pr (|K|PTATOP (|K|Z+ r_pbei r_cbei)) (|K|PTATOP (|K|Z+ r_pbii r_cras)) (|K|PTATOP (|K|Z+ r_pbid r_cras)) (|K|PTATOP (|K|Z+ r_pbed r_cbed)) r_tip)
)

;insertar los encabezados correspondientes a cambios de perfil
(defun |R|INSTIT (r_lprep r_lant)
	(cond
		((null r_lprep) nil)
		((= r_lant (length (car r_lprep)))
			(cons (car r_lprep) (|R|INSTIT (cdr r_lprep) r_lant))
		)
		(T
			(setq r_prep (car r_lprep) r_long (length r_prep))
			(if (> r_long 11)
				(append (|R|TITCD) (list r_prep) (|R|INSTIT (cdr r_lprep) r_long))
				(append (|R|TITCS) (list r_prep) (|R|INSTIT (cdr r_lprep) r_long))
			)
		)
	)
)

;REPLANTEO: replantear un alineamiento
;"|A|REPLANTEO"
(defun |R|REPLANTEO (r_lprg r_dal)
	(defun |R|REPLANT (r_lpr)
		(cond
			((null r_lpr) nil)
			((|R|ENNOREP (caar r_lpr) r_lprnorep)
				(|R|REPLANT (cdr r_lpr))
			)
			((setq r_dvado (|R|ENVADO (caar r_lpr) r_lprvados))
				(cons (|R|PROCVADO (car r_lpr) r_dvado) (|R|REPLANT (cdr r_lpr)))
			)
			(T
				(setq r_dpr (car r_lpr) r_pr (car r_dpr) r_tip (cadr r_dpr) r_cras (|P|ELEV r_pr r_ras)
				      r_lpe (|A|PINS r_pr r_alin) r_pe (car r_lpe) r_dir (cadr r_lpe)
				      r_pt (cdr (|A|CALCVAL r_lperft r_pr)) r_sc (car r_pt) r_ac (cadr r_pt) r_flecha (/ (caddr r_pt) -100)
				      r_adp (cadddr r_pt) r_adsa (nth 4 r_pt) r_dali (nth 5 r_pt) r_dald (nth 6 r_pt) r_nbl (last r_pt)
				      r_lpsa (|A|CALCVAL r_lpersa r_pr) r_peri (/ (car r_lpsa) 100) r_perd (/ (cadr r_lpsa) 100)
				      r_sai (caddr r_lpsa) r_sad (last r_lpsa)
				)
				(if (eq r_adsa "N") (setq r_sai 0.0 r_sad 0.0))
				(if (= r_sc 0)
					(setq r_tc "S" r_lptr (|R|REPS r_pr r_cras r_pe r_dir r_nbl r_sai r_sad r_peri r_perd r_tip))
					(setq r_tc "D" r_lptr (|R|REPD r_pr r_cras r_pe r_dir r_sc r_nbl r_sai r_sad r_peri r_perd r_tip))
				)
				(cons r_lptr (|R|REPLANT (cdr r_lpr)))
			)
		)
	)

	(setq r_nomal (|O|ITEM 1 r_dal) r_alin (|O|ITEM 3 r_dal) r_ras (|O|ITEM 5 r_dal) r_lperft (|O|ITEM 7 r_dal)
	      r_lpersa (|A|LISTPERSA r_nomal r_alin r_lperft) r_lprvados (cadr (|F|LEECSVA r_nomal "vados" 1))
	      r_lprpuentes (cadr (|F|LEECSVA r_nomal "puentes" 1)) r_lprI&R (cadr (|F|LEECSVA r_nomal "retornos" 1))
	      r_lprnorep (|L|INTERC r_lprI&R r_lprpuentes) r_lprtraza (|R|REPLANT r_lprg) r_lrpvados (|R|PPSVADO r_lprvados)
	      r_lprnsr (mapcar 'car r_lprtraza) r_lprtraza (mapcar 'cdr r_lprtraza)
	      r_lprnsb (mapcar 'car r_lprtraza) r_lprtraza (mapcar 'cdr r_lprtraza)
	      r_lprnb (mapcar 'car r_lprtraza) r_lprtraza (mapcar 'cdr r_lprtraza)
	      r_lprnr (mapcar 'car r_lprtraza)
	)
	(setq r_lprvnsr (mapcar 'car r_lrpvados) r_lrpvados (mapcar 'cdr r_lrpvados)
	      r_lprvnsb (mapcar 'car r_lrpvados) r_lrpvados (mapcar 'cdr r_lrpvados)
	      r_lprvnb (mapcar 'car r_lrpvados) r_lrpvados (mapcar 'cdr r_lrpvados)
	      r_lprvnr (mapcar 'car r_lrpvados)
	)
  	(|F|GUARDACSVA r_nomal "Replanteo Nivel Rasante" nil (append (|R|TITG r_nomal) (|R|INSTIT (|L|INTERC r_lprnr r_lprvnr) 0) (|R|CARACT)) T)
  	(|F|GUARDACSVA r_nomal "Replanteo Nivel Base" nil (append (|R|TITG r_nomal) (|R|INSTIT (|L|INTERC r_lprnb r_lprvnb) 0) (|R|CARACT)) T)
  	(|F|GUARDACSVA r_nomal "Replanteo Nivel SubBase" nil (append (|R|TITG r_nomal) (|R|INSTIT (|L|INTERC r_lprnsb r_lprvnsb) 0) (|R|CARACT)) T)
  	(|F|GUARDACSVA r_nomal "Replanteo Nivel SubRasante" nil (append (|R|TITG r_nomal) (|R|INSTIT (|L|INTERC r_lprnsr r_lprvnsr) 0) (|R|CARACT)) T)
	(list (|L|ORDENAR (|L|ELIMDUP r_lbei)) (|L|ORDENAR (|L|ELIMDUP r_lbii)) (|L|ORDENAR (|L|ELIMDUP r_lpeje)) (|L|ORDENAR (|L|ELIMDUP r_lbid)) (|L|ELIMDUP (|L|ORDENAR r_lbed)))
)

;;;;replanteo de puntos de un alineamiento
;;;;"|D|REPAL"
;;;(defun |D|REPAL (d_dal d_pit)
;;;	(defun |D|REPC ()
;;;		(setq d_delta (cadddr d_seg) d_rc (nth 4 d_seg) d_cg (|C|CENTRO d_delta d_rc d_pp d_up) d_tg (|C|LTANG d_delta d_rc)
;;;		      d_ncc (strcat d_nac (|T|ITOC d_nc 2)) d_lps (|A|REPCP d_seg d_pri d_ncc) d_dpc (car d_lps)
;;;		      d_pc (car d_dpc) d_fc (car (last d_lps))
;;;		      d_nv (strcat "V" d_ncc) d_ncg (strcat "CG" d_ncc)
;;;		      d_dv (cdr (assoc (strcat "V" (itoa d_nc)) d_polal)) d_alfa (car d_dv) d_yv (caddr d_dv) d_xv (cadddr d_dv)
;;;		      d_ext (- (|K|DISTH d_cg (list d_xv d_yv)) d_rc) d_des (abs (* d_rc d_delta))
;;;		)
;;;		(|B|INSERT "TRC" d_pit "L_Tablas" 0.0 1.0
;;;			(|T|LISATT (list d_ncc (list "<" d_alfa) (list "<" d_delta) d_rc d_tg d_ext d_des d_nv (list d_yv d_xv) d_ncg (reverse d_cg) d_pc d_pri (reverse d_pp)) T)
;;;		)
;;;		(setq d_pit (|K|Y- d_pit 10) d_cps 0 d_fl T)
;;;		(foreach d_dps d_lps
;;;			(setq d_np (car d_dps) d_pr (cadr d_dps) d_pt (caddr d_dps) d_ac (last d_dps)
;;;			      d_dpi (|K|BPTPS d_pt (cdr (vports))) d_pin (car d_dpi) d_vtwist (cadr d_dpi)
;;;			      d_ai (+ d_ac d_vtwist) d_cps (1+ d_cps) d_npr d_np
;;;			)
;;;			(if (eq (substr d_np 1 2) "PC") (setq d_npr (|T|SEP- d_npa d_np)))
;;;			(if (and (eq (substr d_np 1 2) "FC") (not (eq d_nps "")))
;;;				(setq d_fl nil)
;;;			)
;;;			(if d_fl (|B|INSERT "RPT" d_pin "L_Replanteo" d_ai 2.0 (list d_npr)))
;;;			(if (> d_cps 1)
;;;				(if (< d_cps (length d_lps))
;;;					(|B|INSERT "TRP" d_pit "L_Tablas" 0.0 1.0 (|T|LISATT (list d_np d_pr (reverse d_pt)) T))
;;;					(|B|INSERT "TRF" d_pit "L_Tablas" 0.0 1.0 (|T|LISATT (list d_np d_pr (reverse d_pt)) T))
;;;				)
;;;			)
;;;			(setq d_pit (|K|Y- d_pit 5))
;;;		)
;;;		(setq d_nc (1+ d_nc) d_npa d_fc d_pri d_prf)
;;;	)
;;;	(defun |D|REPR ()
;;;		(setq d_rumbo (|C|RUMBO d_pp d_up) d_an (- (|K|ANG d_pp d_up) (/ PI 2))
;;;		      d_dpi (|K|BPTPS d_pp (cdr (vports))) d_pin (car d_dpi) d_vti (cadr d_dpi)
;;;		      d_dpf (|K|BPTPS d_up (cdr (vports))) d_pfi (car d_dpf) d_vtf (cadr d_dpf)
;;;		      d_ai (+ d_an d_vti) d_af (+ d_an d_vtf) d_fl T
;;;		)
;;;		(if (not (eq d_npa "")) (setq d_npp d_npa) (setq d_npp (strcat "PT" d_nac (|T|ITOC d_np 2)) d_np (1+ d_np)))
;;;		(if (not (eq d_nps "")) (setq d_nup d_nps d_fl nil) (setq d_npp (strcat "PT" d_nac (|T|ITOC d_np 2)) d_np (1+ d_np)))
;;;		(|B|INSERT "TRR" d_pit "L_Tablas" 0.0 1.0 (|T|LISATT (list (list "<" d_rumbo) d_npp d_pri (reverse d_pp) d_nup d_prf (reverse d_pp)) T))
;;;		(|B|INSERT "RPT" d_pin "L_Replanteo" d_ai 2.0 (list d_npp))
;;;		(if d_fl (|B|INSERT "RPT" d_pfi "L_Replanteo" d_af 2.0 (list d_nup)))
;;;		(setq d_pri d_prf d_pit (|K|Y- d_pit 10))
;;;	)
;;;
;;;	(if (not d_pit) (setq d_pit (getpoint "\n punto de inserción de la tabla") d_itit T) (setq d_itit nil))
;;;	(setq d_na (|O|ITEM 0 d_dal) d_nomal (|O|ITEM 1 d_dal) d_polal (|O|ITEM 2 d_dal) d_alin (|O|ITEM 3 d_dal)
;;;	      d_lpr (|A|LISTPR d_dal T nil nil nil nil nil 5.0) d_pref (cadr (|T|LISDATOS d_nomal " ")) d_pri (|A|PRI d_alin)
;;;	      d_nc 1 d_npa "" d_np 1 d_nac (|T|ITOC d_na 2)
;;;	)
;;;	(if d_itit (progn (|B|INSERT "TRT" d_pit "L_Tablas" 0.0 1.0 nil) (setq d_pit (|K|Y- d_pit 20))))
;;;	(|B|INSERT "TRA" d_pit "L_Tablas" 0.0 1.0 (list d_nomal)) (setq d_pit (|K|Y- d_pit 10))
;;;	(foreach d_seg d_alin
;;;		(setq d_pp (car d_seg) d_up (cadr d_seg) d_prf (caddr d_seg) d_tip (last d_seg) d_pseg (|A|PSEG d_up d_alin))
;;;		(if (and d_pseg (eq (last d_pseg) "A")) (setq d_nps (strcat "PC" (itoa (1+ d_nc)))) (setq d_nps ""))
;;;		(cond
;;;			((eq d_tip "A") (|D|REPC))
;;;			(T (|D|REPR))
;;;		)
;;;	)
;;;	d_pit
;;;)
  
;replanteo de puntos singulares
;"|R|REPPS"
(defun |R|REPPS (r_pit)
	(setq r_ntps (|T|GETST nil "nombre de la tabla" T))
	(if (not r_pit) (setq r_pit (getpoint "\n punto de inserción de la tabla") r_itit T) (setq r_itit nil))
	(if r_itit (progn (|B|INSERT "TRPT" r_pit "L_Tablas" 0.0 1.0 nil) (setq r_pit (|K|Y- r_pit 20))))
	(|B|INSERT "TRPN" r_pit "L_Tablas" 0.0 1.0 (list r_ntps)) (setq r_pit (|K|Y- r_pit 10))
	(while (setq r_pt (getpoint "\n marque un punto"))
		(setq r_nps (getstring "\nnombre del punto: "))
		(|B|INSERT "RPT1" (car (|K|TRANS r_pt nil)) "Replanteo" 0.0 1.0 (list r_nps))
		(|B|INSERT "TCXY" r_pit "L_Tablas" 0.0 1.0 (|T|LISATT (list r_nps (|K|PTATOP r_pt)) T))
		(setq r_pit (|K|Y- r_pit 5))
	)
	r_pit
)

(defun C:VERIFREP ()
	(Setq r_lprep (|L|INTERC r_lprnsb r_lprvnsb) r_lay "SB_Replanteo")
	(foreach r_dpr r_lprep
		(setq r_pr (car r_dpr) r_pi (|K|PTATOP (cadr r_dpr)) r_pe (|K|PTATOP (caddr r_dpr)) r_pd (|K|PTATOP (cadddr r_dpr))
		      r_cpi (caddr r_pi) r_cpe (caddr r_pe) r_cpd (caddr r_pd)
		)
		(|B|INSERT "PTO" r_pi "SB_Replanteo" r_dir 0.25 (list (rtos r_pr 2 2) (rtos r_cpi 2 2) "SBaI"))
		(|B|INSERT "PTO" r_pe "SB_Replanteo" r_dir 0.25 (list (rtos r_pr 2 2) (rtos r_cpe 2 2) "SBaE"))
		(|B|INSERT "PTO" r_pd "SB_Replanteo" r_dir 0.25 (list (rtos r_pr 2 2) (rtos r_cpd 2 2) "SBaD"))
	)
)
