;------------------------------------------------------------------------------------------------------------------------------------------------------------------------------------------
;	A	R	M	A	D	O		D	E		P	L	A	N	O	S
;------------------------------------------------------------------------------------------------------------------------------------------------------------------------------------------
(defun |PL|PDOA (pl_ldoa)
	(cond
		((null pl_ldoa) nil)
		(T
			(setq pl_doa (car pl_ldoa) pl_pr (car pl_doa) pl_cde (nth 6 pl_doa) pl_cds (nth 7 pl_doa) pl_ang (|N|GAR (nth 8 pl_doa))
			      pl_sesc (nth 9 pl_doa) pl_obs (last pl_doa) pl_jh 1
			)
			(if (= pl_pr g_pri) (setq pl_pr (+ pl_pr 0.5)))
			(if (= pl_pr g_prf) (setq pl_pr (- pl_pr 0.5)))
			(if (< pl_pr (+ g_pri (* 22.0 g_eschi))) (setq pl_jh 0))
			(if (> pl_pr (- g_prf (* 22.0 g_eschi))) (setq pl_jh 2))
			(if (not (eq pl_obs "Demoler"))
			  (progn
				(setq pl_dpip (|A|PINS pl_pr g_alin) pl_pip (car pl_dpip) pl_dir (cadr pl_dpip) pl_dpip (|K|BPTPS pl_pip (cdr (vports)))
				      pl_pip (car pl_dpip) pl_vtwist (cadr pl_dpip) pl_piti (|K|Y+ pl_pip 12.0) pl_pitd (|K|Y- pl_pip 12.0)
				)
			  	(cond
					((eq pl_sesc "I")
						(|O|TEXT pl_piti pl_piti 3.0 (strcat "CDE:" (rtos pl_cde 2 2)) 0 0.8 0 "ROMANS" 0 pl_jh 2 "L_TEXTOS")
						(|O|TEXT pl_pitd pl_pitd 3.0 (strcat "CDS:" (rtos pl_cds 2 2)) 0 0.8 0 "ROMANS" 0 pl_jh 2 "L_TEXTOS")
					)
					(T
						(|O|TEXT pl_pitd pl_pitd 3.0 (strcat "CDE:" (rtos pl_cde 2 2)) 0 0.8 0 "ROMANS" 0 pl_jh 2 "L_TEXTOS")
						(|O|TEXT pl_piti pl_piti 3.0 (strcat "CDS:" (rtos pl_cds 2 2)) 0 0.8 0 "ROMANS" 0 pl_jh 2 "L_TEXTOS")
					)
				)
			  	(setq pl_pia (|FV|DESP (list pl_pr pl_cde) g_pipl g_pcpl g_defv 1) pl_pia (|K|Y- (car (|K|BPTPS pl_pia (cdr (vports)))) 10.0))
			  	(|O|TEXT pl_pia pl_pia 3.0 (strcat "CDE:" (rtos pl_cde 2 2)) 0 0.8 0 "ROMANS" 0 pl_jh 2 "L_TEXTOS")
			  	(setq pl_pia (|K|Y- pl_pia 5.0))
			  	(|O|TEXT pl_pia pl_pia 3.0 (strcat "CDS:" (rtos pl_cds 2 2)) 0 0.8 0 "ROMANS" 0 pl_jh 2 "L_TEXTOS")
			  )
			)
			(|PL|PDOA (cdr pl_ldoa))
		)
	)
)

;;;(defun |PL|CLA ()
;;;	(setq ss (|L|SSL (ssget "X" '((8 . "E_*")))))
;;;	(foreach ssn ss
;;;		(setq sse (entget ssn) ss8 (|O|ITEM 8 sse) ss8n (strcat "V" (substr ss8 2))
;;;		      sse (|O|REEMP 8 ss8n sse)
;;;		)
;;;		(entmod sse)
;;;	)
;;;)

;"|PL|SN"
(defun |PL|SN()
	(|G|SET0VAR)
	(|SN|TSN (reverse (|SN|SELNUM)))
	(|G|RESTVAR nil)
)

;"|PL|ESCG"
(defun |PL|ESCG ()
	(setq pl_eh (getint "\n escala horizontal: ")
	      pl_ev (getint "\n escala vertical: ")
	      pl_pi (getpoint "\n marque el punto de inserción")
	)
	(|B|ESCG pl_pi pl_eh pl_ev "m")
)

;"|PL|INFOP"
(defun |PL|INFOP ()
	(setq pl_piip (list 607.5 56.5))
	(|O|TEXT pl_piip pl_piip 5.0 (caar g_infpro) 0 0.8 0 "ROMANS" 0 1 2 "L_Titulos")
	(setq pl_piip (|K|Y- pl_piip 6.15))
	(|O|TEXT pl_piip pl_piip 4.5 (caadr g_infpro) 0 0.8 0 "ROMANS" 0 1 2 "L_Titulos")
	(setq pl_piip (|K|Y- pl_piip 6.0))
	(|O|TEXT pl_piip pl_piip 4.5 (caaddr g_infpro) 0 0.8 0 "ROMANS" 0 1 2 "L_Titulos")
	(setq pl_piip (|K|X- (|K|Y- pl_piip 4.5) 72.0))
	(|O|MTEXT pl_piip (car (nth 4 g_infpro)) 3.5 "ROMANS" "L_SubTitulos" 145.0 1)
	(setq pl_piip (list 534.0 11.5))
	(|O|TEXT pl_piip pl_piip 5.0 (car (nth 5 g_infpro)) 0 0.8 0 "ROMANS" 0 0 0 "L_Titulos")
)
;;;(defun C:INFOP ()
;;;	(setq pl_llist (layoutlist) pl_curlo (getvar "CTAB"))
;;;	(foreach pl_layout (cdr pl_llist)
;;;		(setvar "CTAB" pl_layout)
;;;		(|PL|INFOP)
;;;	)
;;;	(setvar "CTAB" pl_curlo)
;;;)

;"|PL|DIBPER"
(defun |PL|DIBPER ()
	(setq pl_lpsa (|L|OBTSLV g_lpersa g_pri g_prf)
	      pl_lm (list (list 65.0 336.0) (list (+ 65.0 (/ (- g_prf g_pri) g_eschi)) 336.0))
	      pl_laye (strcat g_ini "_Rasante") pl_lbi (strcat g_ini "_BIzq") pl_lbd (strcat g_ini "_BDer")
	      pl_dip (car pl_lpsa) pl_lpsa (cdr pl_lpsa) pl_pii (cadr pl_dip) pl_pdi (caddr pl_dip)
	      pl_pibi (|K|Y+ (car pl_lm) pl_pii) pl_pibd (|K|Y+ (car pl_lm) pl_pdi)
	)
	(|O|TEXT '(47.5 346.0) '(47.5 346.0) 3.0 "PERALTES" 0 0.8 0 "ROMANS" 0 1 2 "L_TEXTOS")
	(|O|LINE '(33.0 339.0) '(43.0 339.0) pl_laye)
	(|O|TEXT '(45.0 339.0) '(45.0 339.0) 3.0 "Rasante" 0 0.8 0 "ROMANS" 0 0 2 "L_TEXTOS")
	(|O|LINE '(33.0 334.0) '(43.0 334.0) pl_lbi)
	(|O|TEXT '(45.0 334.0) '(45.0 334.0) 3.0 "Borde Izq." 0 0.8 0 "ROMANS" 0 0 2 "L_TEXTOS")
	(|O|LINE '(33.0 329.0) '(43.0 329.0) pl_lbd)
	(|O|TEXT '(45.0 329.0) '(45.0 329.0) 3.0 "Borde Der." 0 0.8 0 "ROMANS" 0 0 2 "L_TEXTOS")
	(|O|LINE (car pl_lm) (cadr pl_lm) pl_laye)
	(foreach pl_dp pl_lpsa
		(setq pl_pr (car pl_dp) pl_peri (cadr pl_dp) pl_perd (caddr pl_dp)
		      pl_pbi (|K|X+ (|K|Y+ (car pl_lm) pl_peri) (/ (- pl_pr g_pri) g_eschi))
		      pl_pbd (|K|X+ (|K|Y+ (car pl_lm) pl_perd) (/ (- pl_pr g_pri) g_eschi))
		)
		(|O|LINE pl_pibi pl_pbi pl_lbi)
		(|O|LINE pl_pibd pl_pbd pl_lbd)
		(setq pl_pibi pl_pbi pl_pibd pl_pbd)
	)
)

;PDP: poner los datos de planimetría
;"|PL|PDP"
(defun |PL|PDP()
	(|G|SET0VAR)
 	(setq pl_ctab (getvar "CTAB")
	      pl_wpoints (|L|PRIFIN g_wpoints)
	      pl_laypr (strcat g_ini "_Progresivas") pl_layps (strcat g_ini "_Puntos")
	      pl_ldp (|N|SEQNUM (caar pl_wpoints) 100.0 (car (last pl_wpoints)))
	      pl_fl nil pl_lps '()
	      pl_lptf (cadr (|F|LEECSVA g_nomal "Puntos Fijos" 1))
	)
	(cond
		((eq pl_ctab "Model")
			(setq pl_transf nil g_pri g_pria g_prf g_prfa pl_pdv nil)
		)
		((eq (substr pl_ctab 1 2) "PA")
			(setq pl_wpoints (|L|OBTSL pl_wpoints g_pri g_prf)
			      pl_ldp (|L|OBTSL pl_ldp g_pri g_prf) pl_transf T pl_pdv T
			)
		)
		(T
			(setq pl_transf T g_pri g_pria g_prf g_prfa pl_pdv nil pl_ldp (|N|SEQNUM (caar pl_wpoints) 500.0 (car (last pl_wpoints))) pl_lptf nil)
		)
	)
	(foreach pl_dp pl_ldp
		(setq pl_pr (car pl_dp) pl_dpi (|A|PINS pl_pr g_alin) pl_pt (car pl_dpi) pl_an (cadr pl_dpi))
		(if pl_transf
			(if (setq pl_dpr (|K|BPTPS pl_pt (cdr (vports))))
			  (progn
				(setq pl_pt (car pl_dpr) pl_an (+ pl_an (cadr pl_dpr)))
				(|B|INSERT "PR" pl_pt pl_laypr pl_an 1 (list (rtos pl_pr 2 0))) ;(|B|EXPLOT (entlast))
			  )
			)
			(|B|INSERT "PR" pl_pt pl_laypr pl_an 1 (list (rtos pl_pr 2 0))) ;(|B|EXPLOT (entlast))
		)
	)
	(foreach pl_dps pl_wpoints
		(setq pl_pr (car pl_dps) pl_pt (|K|PTATOP (cadr pl_dps)) pl_sg (|N|-SIGNO (caddr pl_dps)) pl_nps (last pl_dps)
		      pl_dir (pl_sg (last (|A|IDP pl_pt g_alin nil)) (* Pi 0.5))
		)
		(if pl_transf (setq pl_dps (|K|BPTPS pl_pt (cdr (vports))) pl_pt (car pl_dps) pl_dir (+ pl_dir (cadr pl_dps))))
		(if (not (eq (substr pl_ctab 1 2) "PG"))
		  (progn
			(|B|INSERT "PRGE" pl_pt pl_laypr pl_dir 1 (list (strcat pl_nps ": Pr. " (rtos pl_pr 2 2)))) (|B|EXPLOT (entlast))
		  )
		)
		(if (eq (substr pl_nps 1 2) "PL")
			(|B|INSERT "PL" pl_pt pl_layps (+ pl_dir (* PI 0.5)) 1 (list pl_nps))
			(if (eq (substr pl_nps 1 2) "CC")
			  (progn
				(setq pl_nv (strcat "V" (substr pl_nps 3)) pl_dp (|L|BUSCAR pl_nv g_polal 0)
				      pl_alfa (cadr pl_dp) pl_pi (|K|PTATOP (cadddr pl_dp)) pl_delta (- pl_alfa PI) pl_rc (nth 4 pl_dp) pl_lee (nth 5 pl_dp) pl_les (nth 6 pl_dp)
				)
			   	(if pl_transf
				      (setq pl_dpv (|K|BPTPS pl_pi (cdr (vports))) pl_pi (car pl_dpv))
				)
			  	(if (< pl_alfa PI)
					(|B|INSERT "VERTI" pl_pi pl_layps (- pl_dir (* PI 0.5)) 1 (list pl_nv))
					(|B|INSERT "VERTD" pl_pi pl_layps (+ pl_dir (* PI 0.5)) 1 (list pl_nv))
				)
			  	(if pl_pdv
						(|B|INSERT "TVERT" (list (- (car pl_pi) 20.0) 581.0) pl_layps 0.0 1 (|T|LISATT (cons pl_nv (|A|ODV pl_nv pl_pr g_alact)) nil))
				)
			  )
			)
		)
	)
	(foreach pl_ptf pl_lptf
		(setq pl_npf (car pl_ptf) pl_pt (list (caddr pl_ptf) (cadr pl_ptf)) pl_elev (cadddr pl_ptf) pl_pr (|T|CTOST (nth 4 pl_ptf))
		      pl_dist (|T|CTOST (nth 5 pl_ptf)) pl_lado (nth 6 pl_ptf)
		      pl_mat (last pl_ptf) pl_att1 pl_npf pl_att2 pl_mat ;pl_att2 (strcat "Pr.:" pl_pr "-" pl_dist "-" pl_lado)
		      pl_att3 (strcat "N: " (rtos (cadr pl_ptf) 2 2)) pl_att4 (strcat "E: " (rtos (caddr pl_ptf) 2 2)) pl_att5 (strcat "Elev: " (rtos pl_elev 2 2))
		)
		(if (or (not pl_lado) (eq pl_lado "N/A")) (setq pl_lado "D"))
		(setq pl_nbptf (strcat "PFijo" pl_lado))
		(if pl_transf
			(if (setq pl_dpr (|K|BPTPS pl_pt (cdr (vports))))
			  (progn
				(setq pl_pt (car pl_dpr))
				(|B|INSERT pl_nbptf pl_pt pl_laypr 0 1 (list pl_att1 pl_att2 pl_att3 pl_att4 pl_att5)) ;(|B|EXPLOT (entlast))
			  )
			)
			(|B|INSERT pl_nbptf pl_pt pl_laypr 0 1 (list pl_att1 pl_att2 pl_att3 pl_att4 pl_att5)) ;(|B|EXPLOT (entlast))
		)
	)
	(if (not pl_pdv)
		(|A|CREATGV g_alact)
	)
	(|G|RESTVAR T)
)

;poner los datos de altimetría del alineamiento actual
;"|PL|PDA"
(defun |PL|PDA ()
	(|G|SET0VAR)
 	(setq pl_ctab (getvar "CTAB") pl_ldg (|A|LISTPR g_alact T T nil nil nil nil (* 25.0 g_eschi))
	      pl_lpend (|P|LISTPENDS g_lpivs nil) pl_fl nil
	)
	(cond
		((eq pl_ctab "Model")
			(setq pl_pi (list (caar g_ras) (cadar g_ras)) pl_pf (list (car (last g_ras)) (cadr (last g_ras))) g_pri (caar pl_ldg) g_prf (car (last pl_ldg))
			      pl_ypiv (+ (cadr g_pipl) g_lgpl 15) pl_fl T pl_lpivs g_lpivs pl_pipl g_pipl pl_pcpl g_pcpl g_eschi 1 pl_eli (cadr pl_pi) pl_elf (cadr pl_pf)
			      pl_px (car g_pipl) pl_py (cadr g_pipl)
			)
		)
		((eq (substr pl_ctab 1 2) "PA")
			(setq pl_nl (atoi (substr pl_ctab 3)) g_prf (* pl_nl g_mxl g_eschi) g_pri (- g_prf (* g_mxl g_eschi)))
			(setq pl_ldg (|L|OBTSL pl_ldg g_pri g_prf) pl_px 65.0 pl_py 146.0
			      pl_pipl (list pl_px pl_py) pl_enta (entget (ssname (ssget (list 60.0 150.0)) 0)) pl_pcpl (atof (substr (|O|ITEM 1 pl_enta) 6))
			      pl_lpivs (|L|OBTSL g_lpivs g_pri g_prf) pl_eli (|P|ELEV g_pri g_ras) pl_elf (|P|ELEV g_prf g_ras) pl_ypiv 297.5 pl_fl T
			      pl_pi (list g_pri (|P|ELEV g_pri g_ras)) pl_pf (list g_prf (|P|ELEV g_prf g_ras))
			)
		)
		(T
			(princ "\n no se puede ejecutar este comando en ") (print pl_ctab)
		)
	)
	(if pl_fl
	  (progn
		(setq pl_ldg (|P|GUITARRA pl_ldg pl_pipl g_terr g_ras g_pri) pl_pid (list pl_px (+ pl_py (* (- pl_eli pl_pcpl) (/ g_defv g_eschi))))
		      pl_pfd (list (+ pl_px (/ (- g_prf g_pri) g_eschi)) (+ pl_py (* (- pl_elf pl_pcpl) (/ g_defv g_eschi)))) pl_flcv T
		)
	  	(foreach pl_dpr pl_ldg
			(setq pl_pt (car pl_dpr) pl_tip (cadr pl_dpr) pl_ptd (list (+ pl_px (/ (- (car pl_pt) g_pri) g_eschi)) (+ pl_py (* (- (cadr pl_pt) pl_pcpl) (/ g_defv g_eschi)))))
			(if (not (eq pl_tip "PIV"))
				(|B|INSERT pl_tip (|K|Y+ pl_ptd 5) (strcat g_ini "_PIVs") 0 1 (list (strcat "Pr:" (rtos (car pl_pt) 2 2) "-(" (rtos (cadr pl_pt) 2 2) ")")))
			)
			(if (or (eq pl_tip "PCV") (eq pl_tip "PIV"))
				(if (not (equal pl_ptd pl_pid 0.01))
					(|B|INSERT "PEND" (|K|PMED pl_pid pl_ptd) (strcat g_ini "_Pendientes") (|K|ANG pl_pid pl_ptd) 1 (list (rtos (* (|P|I pl_pi pl_pt) 100) 2 2)))
				)
			)
			(setq pl_pi pl_pt pl_pid pl_ptd)
		)
		(if (or (eq pl_tip "FCV") (eq pl_tip "PIV"))
			(if (not (equal pl_ptd pl_pfd 0.01))
				(|B|INSERT "PEND" (|K|PMED pl_pid pl_pfd) (strcat g_ini "_Pendientes") (|K|ANG pl_pid pl_pfd) 1 (list (rtos (* (|P|I pl_pi pl_pf) 100) 2 2)))
			)
		)
	  	(foreach pl_piv pl_lpivs
			(setq pl_pr (car pl_piv) pl_cota (cadr pl_piv) pl_lcv (caddr pl_piv) pl_ia (car (|A|CALCVAL pl_lpend (- pl_pr (/ pl_lcv 2))))
			      pl_ip (car (|A|CALCVAL pl_lpend (+ pl_pr (/ pl_lcv 2)))) pl_dp (- pl_ip pl_ia) pl_par (|P|PARAM pl_lcv pl_dp) pl_yv (|P|YV pl_lcv pl_dp)
			      pl_pin (list (+ pl_px (/ (- pl_pr g_pri) g_eschi)) pl_ypiv) pl_piv (list pl_pr pl_cota pl_dp pl_lcv pl_par pl_yv)
			)
			(|B|INSERT "PIV" pl_pin (strcat g_ini "_PIVs") 0 1 (|T|LISATT pl_piv nil))
		)
	  )
	)
	(|G|RESTVAR T)
)

;"|PL|PLANIALT"
(defun |PL|PLANIALT ()
	(defun |PL|CREAL ()
		(setq pl_npa (strcat "PA" (itoa pl_nl)) pl_eii (list 65.0 146.0) pl_esd (list 815.0 296.0))
		(|LO|CREA pl_npa) (|LO|ACTIVAR pl_npa)
		(|B|INSERT "MARCO" (list 0 0) "0" 0 1 (list "PLANIALTIMETRIA" (strcat "Lámina N° " (itoa pl_nl) ": Pr. " (rtos g_pri 2 2) " a Pr. " (rtos g_prf 2 2))
						    	    (strcat "Escalas: H:" (itoa (fix g_esch)) "-V:" (itoa (fix g_escv))) (itoa pl_np) (cadr (|G|FECHA))
					      	      )
		) (command "._zoom" "E")
		(|FV|GRILLAL (/ (- g_prf g_pri) g_eschi) 15.0 pl_eii g_defv 25.0)
		(|B|ESCG '(708.0 356.0) g_esch g_escv "m")
		(|VP|CREA (list 55.0 346.0) (- 584.0 346.0) g_pri g_prf g_prf g_alin nil nil)
		(setq pl_llayf (|O|SELLAY "G_*" T))
		(|VA|CREA pl_eii 15.0 g_pri g_prf (|L|OBTSLV g_terr g_pri g_prf) (|L|OBTSLV g_lpivs g_pri g_prf) g_dpl "G_Textos" pl_llayf)
		(|PL|INFOP)
		(|PL|PDP)
		(|PL|DIBPER)
		(|PL|PDA)
		(|PL|PDOA (|L|OBTSL pl_ldoa g_pri g_prf))
	)

	(|G|SET0VAR)
	(princ "\nDatos para los planos de Planialtimetría")
	(setq g_esch (|N|GETREAL g_esch "Escala Horizontal") g_escv (|N|GETREAL g_escv "Escala Vertical") g_defv (/ g_esch g_escv) g_eschi (/ g_esch 1000.0)
	      g_pri g_pria pl_ldoa (cadr (|F|LEECSVA g_nomal "Obras de arte" 1))
	      g_mxl (* (/ 750.0 1000.0) g_esch) g_prf (+ g_pri g_mxl) pl_nl 1 pl_np (length (layoutlist))
	)
	(if (< g_prfa g_prf) (setq g_prf g_prfa))
	(while (< g_prf g_prfa)
		(|PL|CREAL)
		(setq g_pri g_prf g_prf (min (+ g_prf g_mxl) g_prfa) pl_np (1+ pl_np) pl_nl (1+ pl_nl))
	)
	(|PL|CREAL)
	(|G|RESTVAR T)
)

;"|PL|PGEN"
(defun |PL|PGEN ()
	(|G|SET0VAR)
	(setq pl_esch g_esch pl_eschi g_eschi)
	(cond
		((<= g_prfa 22500.0) (setq g_esch 10000.0 pl_mxl 7500.0))
		((<= g_prfa 45000.0) (setq g_esch 20000.0 pl_mxl 15000.0))
		(T (setq g_esch 25000.0 pl_mxl 18500.0))
	)
	(setq g_pri g_pria g_prf pl_mxl pl_eii (list 60.0 414.0) pl_dh 170.0 g_eschi (/ g_esch 1000.0) pl_nl 1)
	(|LO|CREA "PG") (|LO|ACTIVAR "PG")
	(|B|INSERT "MARCO" (list 0 0) "0" 0 1 (list "PLANIMETRIA GENERAL" (strcat "Pr. " (rtos g_pria 2 2) " a Pr. " (rtos g_prfa 2 2))
					    	    (strcat "Escala: " (itoa (fix g_esch))) "1" (cadr (|G|FECHA))
				      	      )
	) (command "._zoom" "E")
	(|B|ESCG '(708.0 71.0) g_esch nil "m")
	(|PL|INFOP)
	(setq pl_llayf (append (list "CN_SecundariasS" "CN_PrimariasT" "CN_SecundariasT") (|L|BORRA (strcat g_ini "_Eje") (|O|SELLAY (strcat g_ini "_*") T))))
	(while (< g_prf g_prfa)
		(|VP|CREA pl_eii pl_dh g_pri g_prf g_prf g_alin pl_llayf T)
		(setq g_pri g_prf g_prf (+ g_prf pl_mxl) pl_eii (|K|Y- pl_eii (+ pl_dh 10.0)))
	)
	(|VP|CREA pl_eii pl_dh g_pri g_prfa g_prfa g_alin pl_llayf T)
	(|PL|PDP)
	(setq g_esch pl_esch g_eschi pl_eschi)
	(|G|RESTVAR T)
)

;"|PL|PPTYE"
(defun |PL|PPTYE ()
	(defun |PL|CLPT (pl_lpt)
		(cond
			((null pl_lpt) nil)
			(T
				(setq pl_nb (caar pl_lpt) pl_pin (last (car pl_lpt))
				      pl_lpt1 (|L|OBTSLE pl_lpt pl_nb 0 T) pl_lpt (|L|OBTSLE pl_lpt pl_nb 0 nil) pl_lapt '()
				      pl_lzo (apply 'max (mapcar 'cadddr pl_lpt1))
				)
				(foreach pl_dpt pl_lpt1
					(setq pl_lapt (cons (list (cadr pl_dpt) (caddr pl_dpt)) pl_lapt))
				)
				(cons (append (list pl_nb pl_pin pl_lzo) (reverse pl_lapt)) (|PL|CLPT pl_lpt))
			)
		)
	)
	(defun |PL|DIBVP (pl_ptip pl_cv)
		(defun |PL|OBTDPT (pl_lent)
			(cond
				((null pl_lent) nil)
				(T
					(setq pl_ent (car pl_lent) pl_tip (|O|ITEM 0 pl_ent) pl_lay (|O|ITEM 8 pl_ent) pl_nomb (cadr (|T|SUBCH pl_lay "_")))
					(cond
						((eq pl_tip "LINE") (cons (list pl_lay (list (|O|ITEM 10 pl_ent) (|O|ITEM 11 pl_ent))) (|PL|OBTDPT (cdr pl_lent))))
						((eq pl_tip "LWPOLYLINE") (cons (list pl_lay (|A|LISVER pl_ent)) (|PL|OBTDPT (cdr pl_lent))))
						((eq pl_tip "INSERT") (cons (list (|O|ITEM 2 pl_ent) (list (|O|ITEM 10 pl_ent))) (|PL|OBTDPT (cdr pl_lent))))
					)
				)
			)
		)
		(setq pl_nbl (car pl_ptip) pl_pin (cadr pl_ptip) pl_lzo (caddr pl_ptip) pl_lpr (cdddr pl_ptip)
		      pl_eii (|K|X- pl_cv (+ (* (/ pl_lzo 2) (/ 1000.0 pl_esch)) 15.0))
		      pl_esd (|K|Y+ (|K|X+ pl_cv (+ (* (/ pl_lzo 2) (/ 1000.0 pl_esch)) 15.0)) 170.0)
		      pl_pit (|K|Y+ pl_cv 190.0) pl_pist (|K|Y- pl_pit 8.0)
		)
		(|MV|CREA (list pl_eii pl_esd))
		(|MV|ESC pl_esch)
		(|MV|CENTRAR pl_pin)
		(|O|TEXT pl_pit pl_pit 5.0 (strcat "PERFIL TIPO " (|N|ROMANO pl_numpt)) 0 1 0 "ROMANS" 0 1 2 "L_TITULOS")
		(setq pl_dif (car pl_lpr) pl_pri (car pl_dif) pl_prf (cadr pl_dif) pl_lpr (cdr pl_lpr))
		(|O|TEXT pl_pist pl_pist 4.0 (strcat "a aplicar entre Pr. " (rtos pl_pri 2 2) " y Pr. " (rtos pl_prf 2 2)) 0 1 0 "ROMANS" 0 1 2 "L_SUBTITULOS")
		(foreach pl_dif pl_lpr
			(setq pl_pist (|K|Y- pl_pist 6.0) pl_pri (car pl_dif) pl_prf (cadr pl_dif))
			(|O|TEXT pl_pist pl_pist 4.0 (strcat "y entre Pr. " (rtos pl_pri 2 2) " y Pr. " (rtos pl_prf 2 2)) 0 1 0 "ROMANS" 0 1 2 "L_SUBTITULOS")
		)
		(setq pl_dept (|PL|OBTDPT (reverse (cadr (|B|LISTENT pl_nbl)))))
		(foreach pl_ept pl_dept
			(setq pl_tip (car pl_ept) pl_lpts (cadr pl_ept))
		)
	)
	(defun |PL|CLAM (pl_nl pl_np pl_npa)
		(|LO|CREA pl_npa) (|LO|ACTIVAR pl_npa)
		(|B|INSERT "MARCO" (list 0 0) "0" 0 1 (list "PERFIL TIPO Y ESTRUCTURA" (strcat "Lámina N° " (itoa pl_nl) ": Pr. " (rtos g_pria 2 2) " a Pr. " (rtos g_prfa 2 2))
							    	    (strcat "Escalas: H:" (itoa (fix pl_esch)) "-V:" (itoa (fix pl_escv))) (itoa pl_np) (cadr (|G|FECHA))
						      	      )
			) (command "._zoom" "E")
		(|B|ESCG '(708.0 71.0) pl_esch pl_escv "m")
		(|PL|INFOP)
		(setq pl_cont 0)
	)
	(|G|SET0VAR)
	(setq pl_lnbpt '() pl_ldpt (cadr (|F|LEECSVA g_nomal "Perfiles Tipo" 1)))
	(foreach pl_dat pl_ldpt
		(setq pl_pri (cadr pl_dat) pl_prf (caddr pl_dat) pl_nbl (last pl_dat) pl_lzo (+ (nth 9 pl_dat) (nth 10 pl_dat))
		      pl_entpt (entget (ssname (ssget "X" (list (cons -4 "<AND") (cons 0 "INSERT") (cons 2 pl_nbl) (cons 42 2) (cons -4 "AND>"))) 0))
		      pl_pin (|O|ITEM 10 pl_entpt)
		      pl_lnbpt (cons (list pl_nbl pl_pri pl_prf pl_lzo pl_pin) pl_lnbpt)
		)
	)
	(princ "\nDatos para los planos de Perfiles Tipo y Estructura")
	(setq pl_lpt (|PL|CLPT (reverse pl_lnbpt)) pl_cpt (length pl_lpt) pl_pmv (list 430.5 367.0)
	      pl_esch (|N|GETREAL 100.0 "Escala Horizontal") pl_escv (|N|GETREAL 50.0 "Escala Vertical") pl_defv (/ pl_esch pl_escv)
	      pl_nl 1 pl_np (length (layoutlist)) pl_npa (strcat "PT" (itoa pl_nl)) pl_eii nil pl_esd nil pl_numpt 1
	)
	(|PL|CLAM pl_nl pl_np pl_npa)
	(while pl_lpt
		(setq pl_pt (car pl_lpt) pl_lpt (cdr pl_lpt) pl_cont (1+ pl_cont))
		(|PL|DIBVP pl_pt pl_pmv)
		(setq pl_pmv (|K|Y- pl_pmv 260) pl_numpt (1+ pl_numpt))
		(if (and pl_lpt (= pl_cont 2))
			(|PL|CLAM (setq pl_nl (1+ pl_nl)) (setq pl_np (1+ pl_np)) (strcat "PT" (itoa pl_nl)))
		)
	)
)

(defun |PL|PST ()
	(defun |PL|CREALST ()
		(setq pl_npst (strcat "ST" (itoa pl_nl)))
		(|LO|CREA pl_npst) (|LO|ACTIVAR pl_npst)
		(|B|INSERT "MARCO" (list 0 0) "0" 0 1 (list "SECCIONES TRANSVERSALES" (strcat "Lámina N° " (itoa pl_nl) ": Pr. " (rtos g_pri 2 2) " a Pr. " (rtos g_prf 2 2))
						    	    (strcat "Escala: " (itoa pl_esch)) (itoa pl_np) (cadr (|G|FECHA))
					      	      )
		) (command "._zoom" "E")
		(|PL|INFOP)
		(|B|ESCG '(410.0 28.0) pl_esch nil "m")
		(|MV|CREA (list pl_eii pl_esd))
		(|MV|ESC pl_esch)
		(|MV|CENTRAR pl_cv)
	)

	(|G|SET0VAR)
	(setq pl_ldpt (cadr (|F|LEECSVA g_nomal "Perfiles Tipo" 1)) pl_lm&m (|L|M&M (mapcar '(lambda (x) (list (nth 9 x) (nth 10 x))) pl_ldpt))
	      pl_amzo (+ (caar pl_lm&m) (cadar pl_lm&m) 10) pl_cst (length g_lst)
	)
	(if (<= pl_amzo 60)
		(setq pl_esch 250 pl_ccol 3)
		(setq pl_esch 500 pl_ccol 3)
	)
	(setq g_fesc (/ 1000.0 pl_esch) pl_nl 1 pl_np (length (layoutlist))
	      pl_m&m (|L|M&M (mapcar 'cadr g_lst)) pl_m&mx (car pl_m&m) pl_m&my (cadr pl_m&m) pl_lst g_lst
	      pl_htst (* g_fesc (+ (- (car pl_m&my) (cadr pl_m&my)) g_ag 8)) pl_atgst (* g_fesc (+ (- (car pl_m&mx) (cadr pl_m&mx)) (* (+ g_san 3) 2)))
	      pl_eii (list 32.0 60.0) pl_esd (list 828.0 584.0) pl_cfst (fix (/ pl_htst g_fesc (+ g_ag 7))) pl_cstp (* pl_cfst pl_ccol)
	)
	(while pl_lst
		(setq pl_ldivl (|L|DIVL pl_lst pl_cstp) pl_ppl (car pl_ldivl) pl_lst (cadr pl_ldivl)
		      pl_pst (car pl_ppl) pl_ust (last pl_ppl) g_pri (car pl_pst) g_prf (car pl_ust)
		      pl_pi (|K|X- (cadr pl_pst) g_san) pl_pf (|K|Y+ (|K|X+ (list (caadr pl_ust) (car pl_m&my)) g_san) (+ g_ag 7))
		      pl_cv (|K|Y- (|K|PMED pl_pi pl_pf) 1.0)
		)
		(|PL|CREALST)
		(setq pl_np (1+ pl_np) pl_nl (1+ pl_nl))
	)
	(|G|RESTVAR T)
)

(defun |PL|CARATULA ()
	(|O|CREALAY "L_MARCO" 8 "Continuous" nil)
	(|O|CREALAY "L_HOJA" 1 "Continuous" nil)
	(setq pl_nombv (car (layoutlist)))
	(|LO|RENOM pl_nombv "CARAT")
	(|LO|ACTIVAR "CARAT")
	(|O|LWPOLY (list '(0 0) '(841 0) '(841 594) '(0 594)) "L_HOJA" 1)
	(|O|LWPOLY (list '(30 10) '(831 10) '(831 584) '(30 584)) "L_MARCO" 1)
	(command "._zoom" "E")
	(setq pl_piip (list 530.0 540.0))
	(|O|TEXT pl_piip pl_piip 20.0 (caar g_infpro) 0 0.7 0 "ROMANS" 0 1 2 "L_Titulos")
	(setq pl_piip (|K|Y- pl_piip 30.0) pl_txt (caadr g_infpro) pl_txt1 (substr pl_txt 1 28) pl_txt2 (substr pl_txt 29))
	(|O|TEXT pl_piip pl_piip 20.0 pl_txt1 0 0.7 0 "ROMANS" 0 1 2 "L_Titulos")
	(setq pl_piip (|K|Y- pl_piip 30.0))
	(|O|TEXT pl_piip pl_piip 20.0 pl_txt2 0 0.7 0 "ROMANS" 0 1 2 "L_Titulos")
	(setq pl_piip (|K|Y- pl_piip 30.0))
	(|O|TEXT pl_piip pl_piip 20.0 (caaddr g_infpro) 0 0.7 0 "ROMANS" 0 1 2 "L_Titulos")
	(setq pl_piip (|K|Y- pl_piip 40.0))
	(|O|TEXT pl_piip pl_piip 18.0 (car (cadddr g_infpro)) 0 0.7 0 "ROMANS" 0 1 2 "L_Titulos")
	(setq pl_piip (list 40.0 310.0))
	(|O|MTEXT pl_piip (car (nth 4 g_infpro)) 18.0 "ROMANS" "L_Titulos" 420.0 1)
	(setq pl_piip (list 40.0 15.0))
	(|O|TEXT pl_piip pl_piip 18.0 (car (nth 5 g_infpro)) 0 0.8 0 "ROMANS" 0 0 0 "L_Titulos")
	(setq pl_piip (list 821.0 15.0))
	(|O|TEXT pl_piip pl_piip 18.0 (strcase (cadr (|G|FECHA))) 0 0.8 0 "ROMANS" 0 2 0 "L_Titulos")
)
