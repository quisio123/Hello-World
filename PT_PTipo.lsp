;---------------------------------------------------------------------------------------------------------------------------------------------------------------------------------------
;C	R	E	A	R		L	O	S		P	E	R	F	I	L	E	S		T	I	P	O	
;---------------------------------------------------------------------------------------------------------------------------------------------------------------------------------------
;inicializar las variables necesarias para el perfil tipo
(setq pt_vcp (list "pt_cpp1" "pt_cpp2" "pt_cpp3" "pt_cpp4")
      pt_vcpb (list "pt_cpbp1" "pt_cpbp2" "pt_cpbp3" "pt_cpbp4")
      pt_vcpsb (list "pt_cpsbp1" "pt_cpsbp2" "pt_cpsbp3" "pt_cpsbp4")
)

;crear la lista de perfiles tipo
;"|PT|LIST"
(defun |PT|LIST (pt_lpt)
	(cond
		((null pt_lpt) nil)
		(T
			(setq pt_pta (car pt_lpt) pt_pri (cadr pt_pta) pt_prf (caddr pt_pta) pt_pta (cdddr pt_pta))
			(append (list (cons pt_pri pt_pta) (cons pt_prf pt_pta)) (|PT|LIST (cdr pt_lpt)))
		)
	)
)

;calcular el perfil tipo para una progresiva determinada
;"|PT|PTPR"
(defun |PT|PTPR (pt_lpt pt_st)
	(cond
		((null pt_lpt) nil)
		(T
			(setq pt_pta (car pt_lpt) pt_pri (cadr pt_pta) pt_prf (caddr pt_pta))
			(if (and (>= pt_st pt_pri) (<= pt_st pt_prf))
				pt_pta
				(|PT|PTPR (cdr pt_lperft) pt_st)
			)
		)
	)
)

;crear el menu de opciones para el perfil tipo
(setq pt_lobpt (list (cons 0 "Calzada") (cons 1 "Banquina") (cons 2 "Vereda") (cons 3 "Ciclovía") (cons 4 "Calzada Sec")
		     (cons 5 "Cordón") (cons 6 "Baranda") (cons 7 "Talud") (cons 8 "Cuneta") (cons 9 "CTalud") (cons 10 "Alambrado")
	       )
      pt_ltcalz (list (cons 0 "Pavimento Flexible") (cons 1 "Hormigón") (cons 2 "Ripio") (cons 3 "Consolidado"))
      pt_ltcord (list (cons 0 "Integrado") (cons 1 "Normal") (cons 2 "Montable") (cons 3 "Cuneta") (cons 4 "Cuneta Montable") (cons 5 "Separador"))
      pt_ltbar (list (cons 0 "New Jersey") (cons 1 "Flex-Beam"))
      pt_ltcun (list (cons 0 "Solera") (cons 1 "Trapecial revestida") (cons 2 "Vertical revestida"))
      pt_lnbc (list (cons 0 "CINT") (cons 1 "VERT") (cons 2 "CMON") (cons 3 "CCUN") (cons 4 "CCUNM") (cons 5 "CSEP"))
      pt_nbctip (list (cons "CINT" "Integrado") (cons "VERT" "Normal") (cons "CMON" "Montable") (cons "CCUN" "Cuneta") (cons "CCUNM" "Cuneta Montable") (cons "CSEP" "Separador"))
)

;"|PT|MENU"
(defun |PT|MENU (pt_lobd)
	(cond
		((null pt_lobd) "")
		(T
			(strcat (itoa (caar pt_lobd)) "-" (cdar pt_lobd) " " (|PT|MENU (cdr pt_lobd))) 
		)
	)
)

(defun |PT|CREABL (pt_nbl pt_pi pt_lent)
	(defun |PT|DPI (pt_pt)
		(list (|K|DX pt_pi pt_pt) (|K|DY pt_pi pt_pt))
	)
	(setq pt_listent '())
	(foreach pt_nent pt_lent
		(setq pt_ent (entget pt_nent) pt_entn '())
		(foreach pt_item pt_ent
			(if (|N|ENTRE (car pt_item) '(10 15))
				(setq pt_entn (cons (cons (car pt_item) (|PT|DPI (cdr pt_item))) pt_entn))
				(setq pt_entn (cons pt_item pt_entn))
			)
		)
		(setq pt_listent (cons (reverse pt_entn) pt_listent))
	)
	(|B|BLOCK pt_nbl (list 0 0 0) "0" (reverse pt_listent) nil)
)

;CREA: generar los perfiles tipo para el alineamiento actual
(defun |PT|CREA (pt_dal)
	;"|PT|PROCOP"
	(defun |PT|PROCOP (pt_list pt_po pt_desp pt_np pt_inic)
		(defun |PT|PROCCALZ ()
			(defun |PT|DIBEST (pt_pie pt_ana pt_tip)
				(if (setq pt_ees (getreal (strcat "Espesor de la " pt_tip)))
				  (progn
					(if (> pt_asc 0.0)
						(setq pt_ane (+ pt_ana (* (max pt_ees 0.1) 2))
						      pt_p1e (|K|PTP pt_pie (- (max pt_ees 0.1)) (- pt_flecha)) pt_p4e (|K|PTP pt_p1e pt_ane pt_flecha)
						      pt_p2e (|K|Y- pt_p1e pt_ees) pt_p3e (|K|Y- pt_p4e pt_ees) pt_lay (strcat pt_inic "_" pt_tip)
						)
						(setq pt_ane (+ pt_ana (max pt_ees 0.1))
						      pt_p1e pt_pie pt_p4e (|K|PTP pt_p1e pt_ane pt_flecha)
						      pt_p2e (|K|Y- pt_p1e pt_ees) pt_p3e (|K|Y- pt_p4e pt_ees) pt_lay (strcat pt_inic "_" pt_tip)
						)
					)
					(|FV|DIBFORM (list pt_p1e pt_p2e pt_p3e pt_p4e) pt_lay 1 pt_po 0 -1 1) (setq pt_lentc (cons (entlast) pt_lentc))
					(|FV|DIBFORM (list pt_p1e pt_p2e pt_p3e pt_p4e) pt_lay 1 pt_po 0 1 1) (setq pt_lentc (cons (entlast) pt_lentc))
				  )
				)
				(if (eq pt_tip "Base")
					(|PT|DIBEST pt_p2e pt_ane "SubBase")
				)
			)

		  	(setq pt_flecha pt_pnorm pt_an (* pt_ac pt_ncl) pt_es (getreal "espesor de la calzada: ")
			      pt_pti pt_desp pt_ptf (|K|PTP pt_pti pt_an pt_flecha)
			      pt_pi1 (|K|Y- pt_pti pt_es) pt_pi2 (|K|Y- pt_ptf pt_es) pt_lentc '()
			)
			(|FV|DIBFORM (list pt_pti pt_pi1 pt_pi2 pt_ptf) pt_lay 1 pt_po 0 -1 1) (setq pt_lentc (cons (entlast) pt_lentc))
			(|FV|DIBFORM (list pt_pti pt_pi1 pt_pi2 pt_ptf) pt_lay 1 pt_po 0 1 1) (setq pt_lentc (cons (entlast) pt_lentc))
			(|PT|DIBEST pt_pi1 pt_an "Base")
			(list pt_ptf pt_lentc)
		)
		(defun |PT|PROCES()
			(defun |PT|DIBESTS (pt_pie pt_ana pt_tip)
				(if (setq pt_ees (getreal (strcat "Espesor de la " pt_tip)))
				  (progn
					(setq pt_ane (+ pt_ana (* (max pt_ees 0.1) 2))
					      pt_p1e (|K|PTP pt_pie (- (max pt_ees 0.1)) (- pt_flecha)) pt_p4e (|K|PTP pt_p1e pt_ane pt_flecha)
					      pt_p2e (|K|Y- pt_p1e pt_ees) pt_p3e (|K|Y- pt_p4e pt_ees) pt_lay (strcat pt_inic "_" pt_tip "S")
					)
					(|FV|DIBFORM (list pt_p1e pt_p2e pt_p3e pt_p4e) pt_lay 1 pt_po 0 -1 1) (setq pt_lents (cons (entlast) pt_lents))
					(|FV|DIBFORM (list pt_p1e pt_p2e pt_p3e pt_p4e) pt_lay 1 pt_po 0 1 1) (setq pt_lents (cons (entlast) pt_lents))
				  )
				)
				(if (eq pt_tip "Base")
					(|PT|DIBESTS pt_p2e pt_ane "SubBase")
				)
			)
			(princ (strcat "\nDatos para la " pt_nobj "\n"))
			(setq pt_flecha (- (/ (getreal "Pendiente transversal (%): ") 100.0))
			      pt_an (getreal "ancho: ") pt_es (getreal "espesor: ")
			      pt_pti pt_desp pt_ptf (|K|PTP pt_pti pt_an pt_flecha) pt_lents '()
			)
			(if pt_es
			  (progn
				(setq pt_pi1 (|K|Y- pt_pti pt_es) pt_pi2 (|K|Y- pt_ptf pt_es))
				(|FV|DIBFORM (list pt_pti pt_pi1 pt_pi2 pt_ptf) pt_lay 1 pt_po 0 -1 1) (setq pt_lents (cons (entlast) pt_lents))
				(|FV|DIBFORM (list pt_pti pt_pi1 pt_pi2 pt_ptf) pt_lay 1 pt_po 0 1 1) (setq pt_lents (cons (entlast) pt_lents))
			  )
			  (progn
				(|FV|DIBFORM (list pt_pti pt_ptf) pt_lay 1 pt_po 0 -1 1) (setq pt_lents (cons (entlast) pt_lents))
				(|FV|DIBFORM (list pt_pti pt_ptf) pt_lay 1 pt_po 0 1 1) (setq pt_lents (cons (entlast) pt_lents))
			  )
			)
			(|PT|DIBESTS pt_pi1 pt_an "Base")
			(list pt_ptf pt_lents)
		)
		(defun |PT|PROCCORD ()
			(setq pt_mnu (|PT|MENU pt_ltcord)
			      pt_tip (getint (strcat "\nTipo de cordón: " pt_mnu))
			      pt_nbl (|O|ITEM pt_tip pt_lnbc)
			      pt_pti (|K|Y+ (|K|X- pt_po pt_dx) pt_dy)
			      pt_ptd (|K|Y+ (|K|X+ pt_po pt_dx) pt_dy)
			      pt_lentb '()
			)
			(|B|INSERT pt_nbl pt_pti pt_lay 0.0 (list -1 1 1) nil) (setq pt_lentb (cons (entlast) pt_lentb))
			(|B|INSERT pt_nbl pt_ptd pt_lay 0.0 (list 1 1 1) nil) (setq pt_lentb (cons (entlast) pt_lentb))
			(cond
				((eq pt_nbl "CSEP") (list (list (+ pt_dx 0.1) pt_dy) pt_lentb))
				((eq pt_nbl "CCUN") (list (list (+ pt_dx 0.579) (+ pt_dy 0.1279)) pt_lentb))
				((eq pt_nbl "CCUNM") (list (list (+ pt_dx 0.5655) (+ pt_dy 0.054)) pt_lentb))
				((eq pt_nbl "CMON") (list (list (+ pt_dx 0.1865) (+ pt_dy 0.0944)) pt_lentb))
				(T (list (list (+ pt_dx 0.20) (+ pt_dy 0.15)) pt_lentb))
			)
		)
		
		(if pt_list
			(setq pt_nobj (|O|ITEM (car pt_list) pt_lobpt) pt_lay (strcat pt_inic "_" pt_nobj) pt_dx (car pt_desp) pt_dy (cadr pt_desp))
		)
		(cond
			((null pt_list) nil)
			((= (car pt_list) 0)
				(setq pt_dc (|PT|PROCCALZ) pt_ptf (car pt_dc) pt_lentc (cadr pt_dc))
				(append pt_lentc (|PT|PROCOP (cdr pt_list) pt_po pt_ptf pt_np pt_inic))
			)
			((|N|ENTRE (car pt_list) (list 1 4))
				(setq pt_dc (|PT|PROCES) pt_ptf (car pt_dc) pt_lents (cadr pt_dc))
				(append pt_lents (|PT|PROCOP (cdr pt_list) pt_po pt_ptf pt_np pt_inic))
			)
			((eq (car pt_list) 5)
				(setq pt_dc (|PT|PROCCORD) pt_ptf (car pt_dc) pt_lentb (cadr pt_dc))
				(append pt_lentb (|PT|PROCOP (cdr pt_list) pt_po pt_ptf pt_np pt_inic))
			)
			((eq (car pt_list) 6)
				(setq pt_mnu (|PT|MENU pt_ltbar)
				      pt_tip (getint (strcat "\nTipo de baranda: " pt_mnub))
				      pt_lentb '()
				)
				(if (= pt_tip 0) (setq pt_nbl "NJERSEY") (setq pt_nbl "FBEAM"))
				(|B|INSERT pt_nbl pt_po pt_lay 0.0 (list -1 1 1) nil) (setq pt_lentb (cons (entlast) pt_lentb))
				(|B|INSERT pt_nbl pt_po pt_lay 0.0 (list 1 1 1) nil) (setq pt_lentb (cons (entlast) pt_lentb))
				(append pt_lentb (|PT|PROCOP (cdr pt_list) pt_po pt_desp pt_np pt_inic))
			)
			((eq (car pt_list) 7)
				(setq pt_hmin (getreal (strcat "\naltura mínima entre hombro y pie del talud: "))
				      pt_pet (- (getreal "\npendiente del talud (1 en ...): "))
				      pt_pti (list pt_dx pt_dy) pt_ptf (|K|PTP pt_pti (/ (abs pt_pet) pt_hmin) (/ 1.0 pt_pet))
				      pt_lentt '()
				)
				(|FV|DIBFORM (list pt_pti pt_ptf) pt_lay 0 pt_po 0 -1 1) (setq pt_lentt (cons (entlast) pt_lentt))
				(|FV|DIBFORM (list pt_pti pt_ptf) pt_lay 0 pt_po 0 1 1) (setq pt_lentt (cons (entlast) pt_lentt))
				(append pt_lentt (|PT|PROCOP (cdr pt_list) pt_po pt_ptf pt_np pt_inic))
			)
			((eq (car pt_list) 8) 
				(setq pt_hmin (getreal (strcat "\naltura mínima entre el eje y el fondo de cuneta: "))
				      pt_pet (- (getreal "\npendiente del talud (1 en ...): "))
				      pt_as (getreal "\nancho de solera: ")
				      pt_pect (getreal "\npendiente del contratalud (1 en ...): ")
				      pt_pti (list pt_dx pt_dy) pt_ptft (|K|PTP pt_pti (/ (abs pt_pet) pt_hmin) (/ 1.0 pt_pet))
				      pt_pfs (|K|X+ pt_ptft pt_as) pt_ptf (|K|PTP pt_pfs (+ pt_hmin 0.6) (/ 1.0 pt_pect))
				      pt_lentc '()
				)
				(|FV|DIBFORM (list pt_pti pt_ptft pt_pfs pt_ptf) pt_lay 0 pt_po 0 -1 1) (setq pt_lentc (cons (entlast) pt_lentc))
				(|FV|DIBFORM (list pt_pti pt_ptft pt_pfs pt_ptf) pt_lay 0 pt_po 0 1 1) (setq pt_lentc (cons (entlast) pt_lentc))
				(append pt_lentc (|PT|PROCOP (cdr pt_list) pt_po pt_ptf pt_np pt_inic))
			)
			((eq (car pt_list) 9)
				(setq pt_pe (getreal "\npendiente del contratalud (1 en ...): ")
				      pt_pti (list pt_dx pt_dy) pt_ptf (|K|PTP pt_pti (+ pt_hmin 0.6) (/ 1.0 pt_pe))
				      pt_lentc '()
				)
				(|FV|DIBFORM (list pt_pti pt_ptf) pt_lay 0 pt_po 0 -1 1) (setq pt_lentc (cons (entlast) pt_lentc))
				(|FV|DIBFORM (list pt_pti pt_ptf) pt_lay 0 pt_po 0 1 1) (setq pt_lentc (cons (entlast) pt_lentc))
				(append pt_lentc (|PT|PROCOP (cdr pt_list) pt_po pt_ptf pt_np pt_inic))
			)
			((eq (car pt_list) 10)
				(setq pt_ptfi (|K|Y- (|K|X- pt_po pt_azo) 0.6) pt_ptfd (|K|Y+ (|K|X+ pt_po pt_azo) 0.6)
				      pt_nbl "STAL" pt_lenta '()
				)
				(|B|INSERT pt_nbl pt_ptfi pt_lay 0.0 (list -1 1 1) nil) (setq pt_lenta (cons (entlast) pt_lenta))
				(|B|INSERT pt_nbl pt_ptfd pt_lay 0.0 (list 1 1 1) nil) (setq pt_lenta (cons (entlast) pt_lenta))
				(append pt_lenta (|PT|PROCOP (cdr pt_list) pt_po pt_ptfd pt_np pt_inic))
			)
		)
	)
	(defun |PT|GETDATA (pt_pr)
		(setq pt_pri (|N|GETREAL pt_pr "progresiva inicial del perfil") pt_prfa (|A|PRF g_alin)
		      pt_prf (|N|GETREAL pt_prfa "progresiva final del perfil")
		      pt_vd (|N|GETREAL g_vd "Velocidad de Diseño")
		      pt_asc (/ (|N|GETREAL 0 "ancho de la separación central") 2)
		      pt_ncl (|N|GETINT pt_ncl "N° de carriles por sentido de circulación")
		      pt_ac (|N|GETREAL pt_ac "ancho del carril")
		      pt_pnorm (- (/ (|N|GETREAL (* pt_pnorm -100) "Pendiente transversal de la calzada (%): ") 100.0))
		      pt_adp (strcase (|T|GETST "S" "admite peralatado?" nil))
		      pt_ads (strcase (|T|GETST "S" "admite sobreancho?" nil))
		      pt_azo (/ (getreal "ancho de la zona de ocupación: ") 2)
		)
	)
	(defun |PT|DIBBASE ()
		(setq pt_eji (|K|Y- pt_pin 7.5) pt_ejs (|K|Y+ pt_pin 7.5) pt_ejb (|K|Y+ pt_pin 6.0)
		      pt_tit1 (|K|Y+ pt_ejs 2.0) pt_tit2 (|K|Y+ pt_tit1 -0.8) pt_dv 2
		      pt_laye (strcat pt_ini "_Eje") pt_layt (strcat pt_ini "_Titulo") pt_lays (strcat pt_ini "_Subtitulo")
		)
		(command "_.zoom" "C" pt_pin 25)
		(|O|LINE pt_eji pt_ejs pt_laye) (|O|LWPOLY (cdr (|FV|BANDERA pt_ejb)) pt_laye 0) (|O|LWPOLY (cdr (|FV|ESPEJARH (|FV|BANDERA pt_ejb))) pt_laye 0)
		(|O|TEXT pt_tit1 pt_tit1 0.5 (strcat "PERFIL TIPO " (|N|ROMANO pt_np)) 0 1 0 "ROMANS" 0 1 2 pt_layt)
		(|O|TEXT pt_tit2 pt_tit2 0.4 (strcat "a aplicar entre Pr.: " (rtos pt_pri 2 2) " y Pr.: " (rtos pt_prf 2 2)) 0 1 0 "ROMANS" 0 1 2 pt_lays)
		(|O|LINE (|K|Y+ pt_pin 0.6) (|K|Y+ (|K|X+ pt_pin 25.0) 0.6) pt_laytn) (setq pt_letn (cons (entlast) pt_letn))
		(|O|LINE (|K|Y- pt_pin 0.6) (|K|Y- (|K|X- pt_pin 25.0) 0.6) pt_laytn) (setq pt_letn (cons (entlast) pt_letn))
	)

	(setq pt_nomal (|O|ITEM 1 pt_dal) pt_alin (|O|ITEM 3 pt_dal) pt_ini (|T|INICIALES pt_nomal nil "") pt_np 1 pt_pin (|K|XY (getpoint "\n punto de inserción del perfil"))
	      pt_msg1 "\nSeleccione los elementos constitutivos del perfil tipo separandolos con espacios,"
	      pt_msg2 "\ncomenzando desde el eje hacia afuera:\n"  pt_lcpt '()
	      pt_titpt (list (list "N°" "De Pr." "A Pr." "VD" "Sep Calz" "AC" "Flecha" "Ad. Peralte" "Ad. Sobreancho" "Al Izq." "Al Der."))
	      pt_let '() pt_laytn (strcat pt_ini "_Terreno") pt_pnorm g_pern
	)
	(command "_zoom" "C" pt_pin 25.0)
	(|PT|GETDATA (|A|PRI pt_alin))
	(while (< pt_prf pt_prfa)
		(|PT|DIBBASE)
		(setq pt_objs (|T|LISDATOS (getstring T (strcat pt_msg1 pt_msg2 (|PT|MENU pt_lobpt) " ")) " ")
		      pt_lent (|PT|PROCOP pt_objs pt_pin (list 0 0) pt_np pt_ini)
		      pt_nompt (strcat "PT" pt_ini (itoa pt_np))
		      pt_lcpt (cons (list pt_np pt_pri pt_prf pt_vd pt_asc (* pt_ac pt_ncl) pt_pnorm pt_adp pt_ads pt_azo pt_azo pt_nompt) pt_lcpt)
		)
		(|PT|CREABL pt_nompt pt_pin pt_lent)
		(|O|DELENTS (append pt_lent pt_letn))
		(|O|LINE (|K|Y+ pt_pin 1.2) (|K|Y+ (|K|X+ pt_pin 25.0) 1.2) pt_laytn)
		(|O|LINE (|K|Y- pt_pin 1.2) (|K|Y- (|K|X- pt_pin 25.0) 1.2) pt_laytn)
		(|B|INSERT pt_nompt pt_pin "0" 0.0 (list 1 2 1) nil)
	  	(setq pt_letn '() pt_np (1+ pt_np) pt_pin (|K|Y- pt_pin 40.0))
		(command "_zoom" "C" pt_pin 25.0)
		(|PT|GETDATA pt_prf)
	)
	(|PT|DIBBASE)
	(setq pt_objs (|T|LISDATOS (getstring T (strcat pt_msg1 pt_msg2 (|PT|MENU pt_lobpt) " ")) " ")
	      pt_lent (|PT|PROCOP pt_objs pt_pin (list 0 0) pt_np pt_ini)
	      pt_lupt (cons (list pt_np pt_pri pt_prf pt_pin pt_azo) pt_lupt)
	      pt_nompt (strcat "PT" pt_ini (itoa pt_np))
	      pt_lcpt (cons (list pt_np pt_pri pt_prf pt_vd pt_asc (* pt_ac pt_ncl) pt_pnorm pt_adp pt_ads pt_azo pt_azo pt_nompt pt_pin) pt_lcpt)
	)
	(|PT|CREABL pt_nompt pt_pin pt_lent)
	(|O|DELENTS (append pt_lent pt_letn))
	(|O|LINE (|K|Y+ pt_pin 1.2) (|K|Y+ (|K|X+ pt_pin 25.0) 1.2) pt_laytn)
	(|O|LINE (|K|Y- pt_pin 1.2) (|K|Y- (|K|X- pt_pin 25.0) 1.2) pt_laytn)
	(|O|INSERT pt_nompt pt_pin "0" 0.0 (list 1 2 1) nil)
	(setq pt_letn nil pt_lent nil)
	(|F|GUARDACSVA g_nomal "Perfiles Tipo" pt_titpt (reverse pt_lcpt) T)
)

;---------------------------------------------------------------------------------------------------------------------------------------------------------------------------------------
;		C	R	E	A	R		L	O	S		P	L	A	N	O	S		D	E			
;																							
;					P	E	R	F	I	L	E	S		T	I	P	O						
;---------------------------------------------------------------------------------------------------------------------------------------------------------------------------------------
(defun |PT|PLANOS ()
	(defun |PT|CLISTA (pt_lpt)
		(cond
			((null pt_lpt) nil)
			(T
				(setq pt_nb (caar pt_lpt) pt_pin (last (car pt_lpt))
				      pt_lpt1 (|L|OBTSLE pt_lpt pt_nb 0 T) pt_lpt (|L|OBTSLE pt_lpt pt_nb 0 nil) pt_lapt '()
				      pt_lzo (apply 'max (mapcar 'cadddr pt_lpt1))
				)
				(foreach pt_dpt pt_lpt1
					(setq pt_lapt (cons (list (cadr pt_dpt) (caddr pt_dpt)) pt_lapt))
				)
				(cons (append (list pt_nb pt_pin pt_lzo) (reverse pt_lapt)) (|PT|CLPT pt_lpt))
			)
		)
	)
	(defun |PT|OBTDPT (pt_lent)
		(cond
			((null pt_lent) nil)
			(T
				(setq pt_ent (car pt_lent) pt_tip (|O|ITEM 0 pt_ent) pt_lay (|O|ITEM 8 pt_ent))
				(cond
					((eq pt_tip "LINE") (cons (list pt_lay (list (|O|ITEM 10 pt_ent) (|O|ITEM 11 pt_ent))) (|PT|OBTDPT (cdr pt_lent))))
					((eq pt_tip "LWPOLYLINE") (cons (list pt_lay (|A|LISVER pt_ent)) (|PT|OBTDPT (cdr pt_lent))))
					(T (cons (list pt_lay (list (|O|ITEM 10 pt_ent)) (|O|ITEM 2 pt_ent)) (|PT|OBTDPT (cdr pt_lent))))
				)
			)
		)
	)
	(defun |PT|DIBVP (pt_ptip pt_cv)
		(setq pt_nbl (car pt_ptip) pt_pin (cadr pt_ptip) pt_lzo (caddr pt_ptip) pt_lpr (cdddr pt_ptip)
		      pt_eii (|K|X- pt_cv (+ (* (/ pt_lzo 2) (/ 1000.0 pt_esch)) 15.0))
		      pt_esd (|K|Y+ (|K|X+ pt_cv (+ (* (/ pt_lzo 2) (/ 1000.0 pt_esch)) 15.0)) 170.0)
		      pt_pit (|K|Y+ pt_cv 190.0) pt_pist (|K|Y- pt_pit 8.0)
		)
		(|MV|CREA (list pt_eii pt_esd))
		(|MV|ESC pt_esch)
		(|MV|CENTRAR pt_pin)
		(|O|TEXT pt_pit pt_pit 5.0 (strcat "PERFIL TIPO " (|N|ROMANO pt_numpt)) 0 1 0 "ROMANS" 0 1 2 "L_TITULOS")
		(setq pt_dif (car pt_lpr) pt_pri (car pt_dif) pt_prf (cadr pt_dif) pt_lpr (cdr pt_lpr))
		(|O|TEXT pt_pist pt_pist 4.0 (strcat "a aplicar entre Pr. " (rtos pt_pri 2 2) " y Pr. " (rtos pt_prf 2 2)) 0 1 0 "ROMANS" 0 1 2 "L_SUBTITULOS")
		(foreach pt_dif pt_lpr
			(setq pt_pist (|K|Y- pt_pist 6.0) pt_pri (car pt_dif) pt_prf (cadr pt_dif))
			(|O|TEXT pt_pist pt_pist 4.0 (strcat "y entre Pr. " (rtos pt_pri 2 2) " y Pr. " (rtos pt_prf 2 2)) 0 1 0 "ROMANS" 0 1 2 "L_SUBTITULOS")
		)
		(setq pt_dept (|PT|OBTDPT (reverse (cadr (|B|LISTENT pt_nbl))))); pt_lisent
	
	)
	(defun |PT|CLAM (pt_nl pt_np pt_npa)
		(|LO|CREA pt_npa) (|LO|ACTIVAR pt_npa)
		(|B|INSERT "MARCO" (list 0 0) "0" 0 1 (list "PERFIL TIPO Y ESTRUCTURA" (strcat "Lámina N° " (itoa pt_nl) ": Pr. " (rtos g_pria 2 2) " a Pr. " (rtos g_prfa 2 2))
							    	    (strcat "Escalas: H:" (itoa (fix pt_esch)) "-V:" (itoa (fix pt_escv))) (itoa pt_np) (cadr (|G|FECHA))
						      	      )
			) (command "._zoom" "E")
		(|B|ESCG '(708.0 71.0) pt_esch pt_escv "m")
		(setq pt_cont 0)
	)
	(|G|SET0VAR)
	(setq pt_lnbpt '() pt_ldpt (cadr (|F|LEECSVA g_nomal "Perfiles Tipo" 1)))
	(foreach pt_dat pt_ldpt
		(setq pt_pri (cadr pt_dat) pt_prf (caddr pt_dat) pt_nbl (last pt_dat) pt_lzo (+ (nth 9 pt_dat) (nth 10 pt_dat))
		      pt_entpt (entget (ssname (ssget "X" (list (cons -4 "<AND") (cons 0 "INSERT") (cons 2 pt_nbl) (cons 42 2) (cons -4 "AND>"))) 0))
		      pt_pin (|O|ITEM 10 pt_entpt)
		      pt_lnbpt (cons (list pt_nbl pt_pri pt_prf pt_lzo pt_pin) pt_lnbpt)
		)
	)
	(setq pt_lpt (|PT|CLISTA (reverse pt_lnbpt)) pt_cpt (length pt_lpt) pt_pmv (list 430.5 367.0)
	      pt_esch (|N|GETREAL 100.0 "Escala Horizontal") pt_escv (|N|GETREAL 50.0 "Escala Vertical") pt_defv (/ pt_esch pt_escv)
	      pt_nl 1 pt_np (length (layoutlist)) pt_npa (strcat "PT" (itoa pt_nl)) pt_eii nil pt_esd nil pt_numpt 1
	)
	(|PT|CLAM pt_nl pt_np pt_npa)
	(while pt_lpt
		(setq pt_pt (car pt_lpt) pt_lpt (cdr pt_lpt) pt_cont (1+ pt_cont))
		(|PT|DIBVP pt_pt pt_pmv)
		(setq pt_pmv (|K|Y- pt_pmv 260) pt_numpt (1+ pt_numpt))
		(if (and pt_lpt (= pt_cont 2))
			(|PT|CLAM (setq pt_nl (1+ pt_nl)) (setq pt_np (1+ pt_np)) (strcat "PT" (itoa pt_nl)))
		)
	)
)

;---------------------------------------------------------------------------------------------------------------------------------------------------------------------------------------
;		D	I	B	U	J	A	R		L	O	S		P	E	R	F	I	L	E	S		
;																							
;		T	I	P	O		E	N		L	A	S		S	E	C	C	I	O	N	E	S	
;																							
;					T	R	A	N	S	V	E	R	S	A	L	E	S						
;---------------------------------------------------------------------------------------------------------------------------------------------------------------------------------------
(defun |PT|LISTPEND (pt_lista)
	(setq pt_laux '())
	(foreach pt_seg pt_lista
		(if (/= (caar pt_seg) (caadr pt_seg))
			(setq pt_laux (cons (list (|K|PEND (car pt_seg) (cadr pt_seg)) pt_seg) pt_laux))
			(setq pt_laux (cons (list -1 pt_seg) pt_laux))
		)
	)
	(|L|ORDENAR pt_laux)
)

(defun |PT|ELSIM (pt_lsegs)
	(cond
		((null pt_lsegs) nil)
		(T
			(setq pt_seg (car pt_lsegs) pt_lsegs (cdr pt_lsegs) pt_sim (car (member (reverse pt_seg) pt_lsegs)) pt_sim2 (car (member pt_seg pt_lsegs)))
			(if pt_sim
				(|PT|ELSIM (|L|BORRA pt_sim pt_lsegs))
				(if pt_sim2
					(|PT|ELSIM (|L|BORRA pt_sim2 pt_lsegs))
					(cons pt_seg (|PT|ELSIM pt_lsegs))
				)
			)
		)
	)
)
(defun |PT|ELPAR (pt_lsegs)
	(defun |PT|ELSUP (pt_list)
		(cond
			((null pt_list) nil)
;;;			((< (length pt_list) 2) (car pt_list))
			((or (< (caar pt_list) -0.08) (> (caar pt_list) 0.08))
				(cons (cadar pt_list) (|PT|ELSUP (cdr pt_list)))
			)
			((equal (caar pt_list) (caadr pt_list) 0.001)
				(setq pt_dps (car pt_list) pt_ps (cadr pt_dps)
				      pt_dss (cadr pt_list) pt_ss (cadr pt_dss)
				)
				(if (> (cadar pt_ss) (cadar pt_ps))
					(|PT|ELSUP (|L|BPOS 1 pt_list))
					(|PT|ELSUP (cdr pt_list))
				)
			)
			(T
				(cons (cadar pt_list) (|PT|ELSUP (cdr pt_list)))
			)
		)
	)
	(setq pt_lsegs (|PT|LISTPEND pt_lsegs))
	(|L|ORDENAR (|PT|ELSUP pt_lsegs))
)

;"|PT|DIB" dibujar los perfiles tipo en las secciones transversales y calcular las areas de desmonte y terraplén
(defun |PT|DIB (pt_bname pt_pi pt_ac pt_pnorm pt_lps pt_ini pt_est pt_dyci pt_dycd)
	(defun |PT|TRANSPT (pt_pt)
		(cond
			((= (car pt_pt) 0.0)
				(list (car pt_pi) (+ (cadr pt_pi) (cadr pt_pt)))
			)
			((minusp (car pt_pt))
				(|K|Y+ (|K|X+ pt_pi (+ (car pt_pt) (car pt_di))) (+ (cadr pt_pt) (cadr pt_di)))
			)
		  	(T
				(|K|Y+ (|K|X+ pt_pi (+ (car pt_pt) (car pt_dd))) (+ (cadr pt_pt) (cadr pt_dd)))
			)
		)
	)
	(defun |PT|DIBCP (pt_lent)
		(setq pt_lay (|O|ITEM 8 pt_lent) pt_lpts (|A|LISVER pt_lent) pt_pp (car pt_lpts) pt_sp (cadr pt_lpts) pt_tp (caddr pt_lpts) pt_cp (last pt_lpts)
		      pt_dx (|K|DX pt_pp pt_cp) pt_dy (|K|DY pt_pp pt_sp)
		)
		(if (minusp pt_dx)
			(setq pt_cp (|K|PTP pt_pp (- pt_dx pt_sai) pt_peri))
			(setq pt_cp (|K|PTP pt_pp (+ pt_dx pt_sad) pt_perd))
		)
		(setq pt_tp (|K|Y+ pt_cp pt_dy)
		      pt_areap (|GC|GAUSS (list pt_pp pt_sp pt_tp pt_cp))
		      pt_lpest (|FV|DIBFORM (list pt_pp pt_sp pt_tp pt_cp) pt_lay 1 pt_pi 0 1 1)
		)
		(if (minusp pt_dx) (setq pt_lpest (reverse pt_lpest)))
		(list (|A|LISSEG pt_lpest) pt_areap pt_lay)
	)
	(defun |PT|CONSENT (pt_lent)
		(setq pt_nent '() pt_lpts '())
		(foreach pt_item pt_lent
			(if (|N|ENTRE (car pt_item) '(10 15))
				(setq pt_pa (|PT|TRANSPT (cdr pt_item)) pt_nent (cons (cons (car pt_item) pt_pa) pt_nent) pt_lpts (cons pt_pa pt_lpts))
				(setq pt_nent (cons pt_item pt_nent))
			)
		)
		(entmake (reverse pt_nent))
		(if (> (car (last pt_lpts)) (car pt_pi)) (setq pt_lpts (reverse pt_lpts)))
		(list (|A|LISSEG pt_lpts) (|GC|GAUSS pt_lpts) pt_lay)
	)
	(defun |PT|DIBTAL (pt_lent)
		(setq pt_lay (|O|ITEM 8 pt_lent) pt_pp (|O|ITEM 10 pt_lent)
		      pt_npi (|PT|TRANSPT pt_pp) pt_signo (|N|SIGNO (car pt_pp))
		      pt_cter (|P|ELP (car pt_npi) pt_lst) pt_dif (- pt_cter (cadr pt_npi)) pt_lct (* (abs pt_dif) 3.0)
		      pt_tal ((|N|SIGNO pt_dif) (/ 1.0 3.0))
		)
		(if (setq pt_ft (car (|I|INTSA (list pt_npi (|K|PTP pt_npi (pt_signo 20.0) pt_tal)) pt_lsst)))
			(|O|LINE pt_npi pt_ft (strcat pt_ini "_Talud"))
		  (progn
			(setq pt_ft (|K|PTP pt_npi (pt_signo pt_lct) pt_tal))
		  	(|O|LINE pt_npi pt_ft (strcat pt_ini "_Talud"))
;;;		  	(entdel pt_est)
;;;			(setq pt_lst (|L|ORDENAR (cons pt_ft pt_lst)))
;;;			(|O|LWPOLY pt_lst (strcat pt_ini "_Terreno") 0)
;;;			(setq pt_est (entlast))
		  )
		)
		(if (minusp (car pt_pp))
			(list (list (list pt_ft pt_npi)) 0.0 pt_lay)
			(list (list (list pt_npi pt_ft)) 0.0 pt_lay)
		)
	)
	(defun |PT|DIBCUN (pt_lent)
		(setq pt_lay (|O|ITEM 8 pt_lent) pt_lpts (|A|LISVER pt_lent)
		      pt_pp (car pt_lpts) pt_sp (cadr pt_lpts) pt_tp (caddr pt_lpts) pt_cp (cadddr pt_lpts)
		      pt_pendt (/ (|K|DY pt_sp pt_pp) (|K|DX pt_sp pt_pp)) pt_as (|K|DX pt_sp pt_tp) pt_pct (/ (|K|DY pt_cp pt_tp) (|K|DX pt_cp pt_tp))
		      pt_npi (|PT|TRANSPT pt_pp) pt_signo (|N|SIGNO (car pt_pp)) pt_cci (- (cadr pt_pi) pt_dyci) pt_ccd (- (cadr pt_pi) pt_dycd)
		)
		(if (minusp (car pt_pp))
			(setq pt_hcun (- (cadr pt_npi) pt_cci) pt_diab -0.5 pt_pendt (- pt_pendt) pt_pct (- pt_pct))
			(setq pt_hcun (- (cadr pt_npi) pt_ccd) pt_diab 0.5)
		)
		(cond
			((<= pt_hcun 1.5)
				(setq pt_tal pt_pendt pt_bbe pt_npi pt_hc 3.0)
			)
			((and (> pt_hcun 1.5) (<= pt_hcun 3.0))
				(setq pt_tal (- (/ 1.0 3.0)) pt_bbe pt_npi st_hc 5.0)
			)
			((and (> pt_hcun 3.0) (<= pt_hcun 5.0))
				(setq pt_tal (- (/ 1.0 2.0)) pt_bbe (|K|PTP pt_npi pt_diab -0.04) st_hc 20.0)
				(|O|LINE pt_npi pt_bbe (strcat pt_ini "_Banquina"))
				(|B|INSERT "STB" pt_npi (strcat pt_ini "_Baranda") 0 (list (pt_signo 1) 1 1) nil)
			)
			(T
				(setq pt_tal (- (/ 1.0 1.5)) pt_bbe (|K|PTP pt_npi pt_diab -0.04) st_hc 25.0)
				(|O|LINE pt_npi pt_bbe (strcat pt_ini "_Banquina"))
				(|B|INSERT "STB" pt_npi (strcat pt_ini "_Baranda") 0 (list (pt_signo 1) 1 1) nil)
			)
		)
		(setq pt_npi pt_bbe pt_pie (|K|PTP pt_npi (pt_signo (/ pt_hcun (abs pt_tal))) pt_tal)) 
		(if (< (cadr pt_pie) (|P|ELP (car pt_pie) pt_lst))
		  (progn
			(|O|LINE pt_npi pt_pie (strcat pt_ini "_Talud"))
			(setq pt_fs (|K|X+ pt_pie pt_as))
			(|O|LINE pt_pie pt_fs (strcat pt_ini "_Solera"))
			(if (setq pt_hct (car (|I|INTSA (list pt_fs (|K|PTP pt_fs (pt_signo 20.0) pt_pct)) pt_lsst)))
				(|O|LINE pt_fs pt_hct (strcat pt_ini "_CTalud"))
			  (progn
				(setq pt_cter (|P|ELP (car pt_fs) pt_lst) pt_dif (- pt_cter (cadr pt_fs)) pt_lct (abs (/ pt_dif pt_pct))
				      pt_hct (|K|PTP pt_fs (pt_signo pt_lct) pt_pct)
				)
			  	(|O|LINE pt_fs pt_hct (strcat pt_ini "_CTalud"))
;;;			  	(entdel pt_est)
;;;			  	(setq pt_lst (|L|ORDENAR (cons pt_hct pt_lst)))
;;;			  	(|O|LWPOLY pt_lst (strcat pt_ini "_Terreno") 0)
;;;			   	(setq pt_est (entlast))
			  )
			)
			(setq pt_lpcun (list pt_npi pt_pie pt_fs pt_hct))
		  )
			(if (setq pt_pie (last (|I|INTSA (list pt_npi (|K|PTP pt_npi (pt_signo (/ pt_hc (abs pt_tal))) pt_tal)) (|A|LISSEG pt_lst))))
			  (progn
				(|O|LINE pt_npi pt_pie (strcat pt_ini "_Talud"))
			  	(setq pt_lpcun (list pt_npi pt_pie))
			  )
			)
		)
		(if (minusp (car pt_pp)) (setq pt_lpcun (reverse pt_lpcun)))
		(list (|A|LISSEG pt_lpcun) 0.0 pt_lay)
	)
	(defun |PT|PROCDENT ()
		(setq pt_lse (car pt_dent) pt_area (cadr pt_dent) pt_laye (caddr pt_dent))
		(cond
			((wcmatch pt_laye "*Calz*") (setq pt_acalz (+ pt_acalz pt_area)))
			((wcmatch pt_laye "*Base*") (setq pt_abase (+ pt_abase pt_area)))
			((wcmatch pt_laye "*SubB*") (setq pt_asbase (+ pt_sbase pt_area)))
			((wcmatch pt_laye "*Cicl*") (setq pt_acicl (+ pt_acicl pt_area)))
			((wcmatch pt_laye "*Vered*") (setq pt_avereda (+ pt_avereda pt_area)))
		)
		(setq pt_lsinf (append pt_lsinf pt_lse))
	)
	(defun |PT|ORDSINF (pt_lord pt_lsi / pt_pp)
		(defun |PT|BUSCS (pt_lsl pt_pini)
			(cond
				((null pt_lsl) nil)
				((equal (caar pt_lsl) pt_pini 0.01)
					(cons (car pt_lsl) (|PT|BUSCS (cdr pt_lsl) pt_pini))
				)
				(T (|PT|BUSCS (cdr pt_lsl) pt_pini))
			)
		)
		(defun |PT|SELS (pt_lsegs pt_pa)
			(setq pt_laux '())
		  	(foreach pt_seg pt_lsegs
				(setq pt_an (|N|ANGBAR (car pt_seg) pt_pa (cadr pt_seg))
				      pt_laux (cons (list pt_an pt_seg) pt_laux)
				)
			)
			(cadr (car (|L|ORDENAR pt_laux)))
		)
		(defun |PT|PSALTOS (pt_pa pt_up pt_lsegs)
			(setq pt_laux '())
			(foreach pt_seg pt_lsegs
				(setq pt_dist (|K|DISTH pt_up (car pt_seg))
				      pt_laux (cons (list pt_dist pt_seg) pt_laux)
				)
			)
			(cadr (car (|L|ORDENAR pt_laux)))
		)

		(setq pt_us (last pt_lord) pt_pp (car pt_us) pt_pb (cadr pt_us))
		(cond
			((equal pt_pb pt_ultp g_tol) pt_lord)
			(T
				(setq pt_lsp (|PT|BUSCS pt_lsi pt_pb))
				(cond
					((null pt_lsp)
						(setq pt_pseg (|PT|PSALTOS pt_pp pt_pb pt_lsi) pt_lsi (|L|BORRA pt_pseg pt_lsi))
						(|PT|ORDSINF (append pt_lord (list (list pt_pb (car pt_pseg)) pt_pseg)) pt_lsi)
					)
					((= (length pt_lsp) 1)
						(setq pt_lsi (|L|BORRA (car pt_lsp) pt_lsi))
						(|PT|ORDSINF (append pt_lord pt_lsp) pt_lsi)
					)
					(T
						(if (setq pt_pseg (|PT|SELS pt_lsp pt_pp))
						  (progn
						  	(setq pt_lsi (|L|BORRA pt_pseg pt_lsi))
							(|PT|ORDSINF (append pt_lord (list pt_pseg)) pt_lsi)
						  )
						  (progn
							(setq pt_pseg (|PT|PSALTOS pt_pp pt_pb pt_lsi) pt_lsi (|L|BORRA pt_pseg pt_lsi))
							(|PT|ORDSINF (append pt_lord (list (list pt_pb (car pt_pseg)) pt_pseg)) pt_lsi)
						  )
						)
					)
				)
			)
		)
	)
	(defun |PT|PRISEG (pt_lsegs)
		(setq pt_x (car pt_pi) pt_pris nil)
		(foreach pt_seg pt_lsegs
			(setq pt_x1p (caar pt_seg))
			(if (< pt_x1p pt_x)
				(setq pt_pris pt_seg pt_x pt_x1p)
			)
		)
		pt_pris
	)

	(defun |PT|UPT (pt_lsegs)
		(setq pt_x (car pt_pi) pt_pris nil)
		(foreach pt_seg pt_lsegs
			(setq pt_x1p (car (cadr pt_seg)))
			(if (> pt_x1p pt_x)
				(setq pt_up (cadr pt_seg) pt_x pt_x1p)
			)
		)
		pt_up
	)

	(setq pt_lisent (cadr (|B|LISTENT pt_bname)) pt_peri (/ (car pt_lps) 100.0) pt_perd (/ (cadr pt_lps) 100.0) pt_sai (caddr pt_lps) pt_sad (cadddr pt_lps)
	      pt_di (list (- pt_sai) (- (* (+ pt_ac pt_sai) pt_peri) (* pt_ac pt_pnorm)))
	      pt_dd (list pt_sad (- (* (+ pt_ac pt_sad) pt_perd) (* pt_ac pt_pnorm)))
	      pt_lcalz (mapcar '(lambda (x) (strcat pt_ini x)) (list "_Calzada" "_Base" "_SubBase"))
	      pt_lst (|A|LVPOLI pt_est) pt_acalz 0.0 pt_abase 0.0 pt_asbase 0.0 pt_acicl 0.0 pt_avereda 0.0
	      pt_lsinf '() pt_lsst (|A|LISSEG pt_lst)
	)
	(while (setq pt_ent (car pt_lisent))
		(setq pt_lisent (cdr pt_lisent))
		(cond
			((eq (|O|ITEM 0 pt_ent) "INSERT")
				(setq pt_ip (|K|XY (|O|ITEM 10 pt_ent)) pt_nbl (|O|ITEM 2 pt_ent) pt_ex (|O|ITEM 41 pt_ent) pt_lay (|O|ITEM 8 pt_ent) pt_dent nil)
				(|B|INSERT pt_nbl (|PT|TRANSPT pt_ip) pt_lay 0 (list pt_ex 1 1) nil)
			)
			((member (|O|ITEM 8 pt_ent) pt_lcalz)
				(setq pt_dent (|PT|DIBCP pt_ent))
			)
			((eq (|O|ITEM 8 pt_ent) (strcat pt_ini "_Cuneta"))
				(setq pt_dent (|PT|DIBCUN pt_ent))
			)
			((wcmatch (|O|ITEM 8 pt_ent) "*Talud")
				(setq pt_dent (|PT|DIBTAL pt_ent))
			)
			(T (setq pt_dent (|PT|CONSENT pt_ent)))
		)
		(if pt_dent (|PT|PROCDENT))
	)
	(setq pt_lsinf (|PT|ELSIM pt_lsinf) pt_lsinf (|PT|ELPAR pt_lsinf)
	      pt_1seg (car pt_lsinf) pt_lsinf (cdr pt_lsinf) pt_ultp (|PT|UPT pt_lsinf)
	      pt_lsinf (|PT|ORDSINF (list pt_1seg) pt_lsinf)
	)
	(|Z|GETAREAS (|A|LISSEG (|A|LISTAV pt_lsinf)) pt_lsst nil)
)
