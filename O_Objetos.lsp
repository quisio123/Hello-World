(setq o_ltbase (entget (tblobjname "LTYPE" "Continuous"))
      o_stbase (entget (tblobjname "STYLE" "Standard"))
      o_dictname (namedobjdict)
)

;crear una variable a partir de un texto y un prefijo
;"|O|SET"
(defun |O|SET (o_pref o_texto o_valor)
	(set (read (strcat o_pref o_texto)) o_valor)
)

;evaluar si existe una variable
;"|O|EVAL"
(defun |O|EVAL (o_nomvar)
	(eval (car (atoms-family 0 (list o_nomvar))))
)

;extraer entidades por capa
;"|O|EXTENT"
(defun |O|EXTENT (o_capa)
	(setq o_ss (ssget "X"))
	(if (not o_capa)
		(setq o_capa "Entidades")
	)
	(setq o_ssl (sslength o_ss) o_lisent '() o_c 1)
	(setq o_fent (open (strcat g_path o_capa ".lsp") "w") o_nocodes (list -1 0 5 330 67 410 340) o_partcodes (list 10 11 12 210))
	(while (setq o_ssn (ssname o_ss (setq o_ssl (1- o_ssl))))
		(setq o_lisent (cons o_ssn o_lisent))
	)
	(if o_lisent
		(foreach o_ssn o_lisent
			(setq o_ent (entget o_ssn) o_tent (|O|ITEM 0 o_ent))
			(if (eq (|O|ITEM 8 o_ent) o_capa)
			  (progn
				(setq o_strl (strcat "(setq o_" (itoa o_c) " (list (cons 0 \"" (|O|ITEM 0 o_ent) "\") ") o_strl2 nil)
				(foreach o_item o_ent
					(if (> (strlen o_strl) 200) (setq o_strl2 o_strl o_strl ""))
					(setq o_code (car o_item) o_rest (cdr o_item))
					(if (not (member o_code o_nocodes))
					(progn
						(if (not (member o_code o_partcodes))
							(setq o_strl (strcat o_strl "(cons " (itoa o_code)))
							(setq o_strl (strcat o_strl "(list " (itoa o_code)))
						)
						(setq o_tipo (type o_rest))
						(cond ((eq o_tipo 'INT)
								(setq o_strl (strcat o_strl " " (itoa o_rest)))
							)
							((eq o_tipo 'REAL)
								(setq o_strl (strcat o_strl " " (rtos o_rest 2 5)))
							)
							((eq o_tipo 'LIST)
								(foreach o_sitem o_rest
									(setq o_strl (strcat o_strl " " (rtos o_sitem 2 5)))
								)
							)
							(T
								(setq o_strl (strcat o_strl  " \"" o_rest "\""))
							)
						)
						(setq o_strl (strcat o_strl ") "))
					))		
					(if o_strl2 (progn (write-line o_strl2 o_fent) (setq o_strl2 nil)))
				)
				(setq o_strl (strcat o_strl "))") o_c (1+ o_c))
				(write-line o_strl o_fent)
			  )
			)
		)
	)
	(close o_fent)
)

(defun |O|ITEM (o_n o_ent)
	(cdr (assoc o_n o_ent))
)

(defun |O|REEMP (o_n o_nv o_lva)
	(subst (cons o_n o_nv) (assoc o_n o_lva) o_lva)
)

;------------------------------------------------------------------------------------------------------------------------------------------------------------------------------------------------------------
;					O	B	J	E	T	O	S		N	O		G	R	A	F	I	C	O	S
;------------------------------------------------------------------------------------------------------------------------------------------------------------------------------------------------------------
;"|O|BUSCAR"
(defun |O|BUSCAR (o_tipo o_nomb)
	(tblsearch o_tipo o_nomb)
)

;"|O|OBTNOMB"
(defun |O|OBTNOMB (o_tipo o_nomb)
	(tblobjname o_tipo o_nomb)
)

;"|O|CREATEXTST"
(defun |O|CREATEXTST (o_list)
	(if (not o_th) (setq o_th 0)) 
	(if (not o_tw) (setq o_tw 1)) 
	(if (not (|O|BUSCAR "Style" (car o_list)))
		(entmakex (list (cons 0 "STYLE")
					(cons 100 "AcDbSymbolTableRecord")
					(cons 100 "AcDbTextStyleTableRecord")
					(cons 2 (car o_list))
					(cons 70 0)
					(cons 40 (caddr o_list))
					(cons 41 (cadddr o_list))
					(cons 50 (nth 4 o_list))
					(cons 71 0)
					(cons 3 (cadr o_list))
					(cons 4 "")
				)
		)
	)
	(if (last o_list) (setvar "TEXTSTYLE" (car o_list)))
)

;"|O|CHECKTSTYLE"
(defun |O|CHECKTSTYLE (o_lista)
	(cond
		((null o_lista) nil)
		(T
			(if (not (|O|BUSCAR "Style" (caar o_lista)))
				(|O|CREATEXTST (car o_lista))
			)
			(|O|CHECKTSTYLE (cdr o_lista))
		)
	)
)

;"|O|CARGASH"
;;;(defun |O|CARGASH (o_name)
;;;	(if (not (|O|BUSCAR "Style" ""))
;;;		(entmakex (list (cons 0 "STYLE")
;;;					(cons 100 "AcDbSymbolTableRecord")
;;;					(cons 100 "AcDbTextStyleTableRecord")
;;;					(cons 2 "")
;;;					(cons 70 1)
;;;					(cons 40 0.0)
;;;					(cons 41 1.0)
;;;					(cons 50 0.0)
;;;					(cons 71 0)
;;;					(cons 42 2.5)
;;;					(cons 3 o_name)
;;;					(cons 4 "")
;;;				)
;;;		)
;;;	)
;;;	(|O|OBTNOMB "STYLE" "")
;;;)

;"|O|CHECKSHAPE"
;;;(defun |O|CHECKSHAPE (o_shape)
;;;	(setq o_ename (|O|OBTNOMB "STYLE" ""))
;;;	(cond
;;;		((null o_ename) (|O|CARGASH o_shape))
;;;		((eq (|O|ITEM 3 (entget o_ename)) o_shape)
;;;			o_ename
;;;		)
;;;		(T nil)
;;;	)
;;;)

;"|O|LOADLTYPE"
(defun |O|LOADLTYPE (o_nomb o_file)
	(cond
		((null o_file)
			(|O|LOADLTYPE o_nomb (strcat g_acadvial "Acadvial.lin"))
		)
		(T (if (not (|O|BUSCAR "ltype" o_nomb))
			(command "-linetype" "L" o_nomb o_file "")
		   )
		)
	)
)

;"|O|CREALTYPE"
;;;(defun |O|CREALTYPE (o_nomb)
;;;	(cond
;;;		((|O|BUSCAR "LTYPE" o_nomb) o_nomb)
;;;		(T
;;;			(setq o_ldef (|O|EVAL (|O|ITEM o_nomb tl_lltype)))
;;;			(entmake o_ldef)
;;;		)
;;;	)
;;;)

;"|O|CHECKLSTYLE"
(defun |O|CHECKLSTYLE (o_lista)
	(cond
		((null o_lista) T)
		((|O|BUSCAR "ltype" (car o_lista))
			(|O|CHECKLSTYLE (cdr o_lista))
		)
		(T
			(|O|LOADLTYPE (car o_lista) nil)
			(|O|CHECKLSTYLE (cdr o_lista))
		)
	)
	(reverse o_ldep)
)

;"|O|SELLAY"
(defun |O|SELLAY (o_wcp o_rew)
	(setq o_dlay (tblnext "LAYER" o_rew) o_layn (|O|ITEM 2 o_dlay))
	(cond
		((null o_dlay) nil)
		((wcmatch o_layn o_wcp)
			(cons o_layn (|O|SELLAY o_wcp nil))
		)
		(T (|O|SELLAY o_wcp nil))
	)
)

;"|O|CREALAY"
(defun |O|CREALAY (o_nomb o_color o_tlin o_act)
	(|O|LOADLTYPE o_tlin nil)
	(if (not (|O|BUSCAR "Layer" o_nomb))
		(entmake (list (cons 0 "layer")
					(cons 100 "AcDbSymbolTableRecord")
					(cons 100 "AcDbLayerTableRecord")
					(cons 2 o_nomb)
					(cons 70 0)
					(cons 62 o_color)
					(cons 6 o_tlin)
					(cons 370 -3)
				)
		)
	)
	(if o_act (|O|ACTLAY o_nomb))
)

;"|O|ACTLAY"
(defun |O|ACTLAY (o_nomb)
	(if (|O|BUSCAR "Layer" o_nomb)
		(|O|DESFRIZAR o_nomb)
		(|O|CREALAY o_nomb 7 "Continuous" nil)
	)
	(setvar "CLAYER" o_nomb)
)

;"|O|FRIZADA"
(defun |O|FRIZADA (o_nomb)
	(if (setq o_lbase (|O|BUSCAR "Layer" o_nomb))
		(progn
			(setq o_cod (|O|ITEM 70 o_lbase))
			(if (= o_cod 1) T nil)
		)
		nil
	)
)

;"|O|DESFRIZAR"
(defun |O|DESFRIZAR (o_nomb)
	(if (setq o_lbase (|O|BUSCAR "Layer" o_nomb))
		(command "_layer" "T" o_nomb "")
	)
)

;"|O|FRIZAR"
(defun |O|FRIZAR (o_nomb)
	(if (setq o_lbase (|O|BUSCAR "Layer" o_nomb))
		(command "_layer" "F" o_nomb "")
	)
)

;devolver una lista con las layers frizadas
(defun |O|LISTLF (o_rew)
	(setq o_dlay (tblnext "LAYER" o_rew) o_layn (|O|ITEM 2 o_dlay))
	(cond
		((null o_dlay) nil)
		((|O|FRIZADA o_layn)
			(cons o_layn (|O|LISTLF nil))
		)
		(T (|O|LISTLF nil))
	)
)
;------------------------------------------------------------------------------------------------------------------------------------------------------------------------------------------------------------
;								L	A	Y	O	U	T	S
;------------------------------------------------------------------------------------------------------------------------------------------------------------------------------------------------------------
(dictnext o_dictname T)
(setq o_dd (dictnext o_dictname) o_nlayout (|O|ITEM 3 o_dd))
(while (not o_nlayout)
	(setq o_dd (dictnext o_dictname) o_nlayout (|O|ITEM 3 o_dd))
)
(setq o_layobj (entget (|O|ITEM 350 o_dd)) o_lps '())
(foreach o_item o_layobj
	(setq o_lps (cons o_item o_lps))
)
(setq o_llayout (layoutlist))

(defun |O|GETLAYOUT (o_loname)
	(dictnext o_dictname T)
	(setq o_llayout (layoutlist))
	(setq o_dd (dictnext o_dictname) o_nlayout (|O|ITEM 3 o_dd))
	(while (or (not o_nlayout) (not (member o_nlayout o_llayout)))
		(setq o_dd (dictnext o_dictname) o_nlayout (|O|ITEM 3 o_dd))
	)
	(setq o_llout (member (cons 3 o_nlayout) o_dd))
	(while (not (= o_nlayout o_loname))
		(setq o_dd (cddr o_dd) o_nlayout (|O|ITEM 3 o_dd))
	)
	(|O|ITEM 350 o_dd)
)

(setq o_dplot (list (cons 1 "") (cons 2 "HP Deskjet 9800 Printer") (cons 4 "A3")
		    (cons 40 3.96875) (cons 41 15.0177) (cons 42 4.014108) (cons 43 3.17499) (cons 44 296.968) (cons 45 419.989)
		    (cons 46 0.0) (cons 47 0.0) (cons 48 30.0) (cons 49 10.0)
		    (cons 141 831.0) (cons 141 584.0) (cons 142 1.0) (cons 143 2.0)
		    (cons 70 688) (cons 72 1) (cons 73 3) (cons 74 5)
		    (cons 7 "Ploteos A3.ctb") (cons 75 17)
		    (cons 147 0.5) (cons 76 1) (cons 77 2) (cons 78 300)
		    (cons 148 -30.0) (cons 149 -10.0)
	      )
)
(defun |O|PSETUP (o_loname)
	(setq o_enlout (|O|GETLAYOUT o_loname) o_entlo (entget o_enlout)
	      o_posi (|L|POS (cons 100 "AcDbPlotSettings") o_entlo)
	      o_posf (|L|POS (cons 100 "AcDbLayout") o_entlo)
	      o_ppl (|L|SUBL o_entlo (1+ o_posi)) o_upl (|L|RESL o_entlo o_posf) o_upl (|O|REEMP 10 (list -0.0354652 1.97784 0.0) o_upl)
	      o_upl (|O|REEMP 11 (list 839.943 595.914 0.0) o_upl) o_upl (|O|REEMP 15 (list 841.0 594.0 0.0) o_upl)
	      o_entlo (append o_ppl o_dplot o_upl)
	)
	(entmod o_entlo) (entupd o_enlout)
)
(defun |O|LIMVP (o_pc o_an o_alt / o_dimp)
    (setq o_dimp (list (/ o_an 2) (/ o_alt 2))
	  o_eii (mapcar '- o_pc o_dimp) o_esd (mapcar '+ o_pc o_dimp)
	  o_esi (list (car o_eii) (cadr o_esd)) o_eid (list (car o_esd) (cadr o_eii)) 
    )
    (list o_eii o_esi o_esd o_eid)
)

;determinar en que viewport cae un punto del layout
(defun |O|GETVP (o_psp o_layout)
	(setq o_ssvp (|L|SSL (ssget "X" '((0 . "VIEWPORT")))))
	(while o_ssvp
		(setq o_nvpt (car o_ssvp) o_vpt (entget o_nvpt) o_vptab (|O|ITEM 410 o_vpt) o_ssvp (cdr o_ssvp))
		(if (eq o_vptab o_layout)
		  (progn
			(setq o_pcps (|O|ITEM 10 o_vpt) o_ancho (|O|ITEM 40 o_vpt) o_altura (|O|ITEM 41 o_vpt)
			      o_evpt (|O|LIMVP o_pcps o_ancho o_altura) o_vpid (|O|ITEM 69 o_vpt)
			)
			(if (|S|DENTRO o_psp o_evpt)
			  (progn
				(setq o_ssvp nil)
			  )
			)
		  )
		)
	)
	o_nvpt
)

;devolver el viewport n del layout
(defun |O|GETVPN (o_id o_layout)
	(setq o_ssvp (|L|SSL (ssget "X" '((0 . "VIEWPORT")))))
	(while o_ssvp
		(setq o_nvpt (car o_ssvp) o_vpt (entget o_nvpt) o_vptab (|O|ITEM 410 o_vpt) o_vpid (|O|ITEM 69 o_vpt) o_ssvp (cdr o_ssvp))
		(if (and (eq o_vptab o_layout) (= o_vpid o_id))
			(setq o_ssvp nil)
		)
	)
	o_nvpt
)
;------------------------------------------------------------------------------------------------------------------------------------------------------------------------------------------------------------
;					E	N	T	I	D	A	D	E	S		G	R	A	F	I	C	A	S
;------------------------------------------------------------------------------------------------------------------------------------------------------------------------------------------------------------
;"|O|3DFACE"
(defun |O|3DFACE (o_p1 o_p2 o_p3 o_p4 o_lay)
	(setq o_ctab (getvar "CTAB"))
  	(if (eq o_ctab "Model") (setq o_tile 0) (setq o_tile 1))
	(entmake 	(list (cons 0 "3DFACE")
				(cons 100 "AcDbEntity")
				(cons 8 o_lay)
				(cons 100 "AcDbFace")
				(cons 10 o_p1)
				(cons 11 o_p2)
				(cons 12 O_p3)
				(cons 13 o_p4)
			)
	)
)

;"|O|ARC"
(defun |O|ARC (o_cen o_rad o_Angi o_Angf o_lay)
	(setq o_ctab (getvar "CTAB"))
  	(if (eq o_ctab "Model") (setq o_tile 0) (setq o_tile 1))
	(entmake 	(list (cons 0 "ARC")
				(cons 100 "AcDbEntity")
				(cons 8 o_lay)
				(cons 10 o_cen)
				(cons 40 o_rad)
				(cons 50 o_Angi)
				(cons 51 o_Angf)
			)
	)
)

;"|O|CIRCLE"
(defun |O|CIRCLE (o_cen o_rad o_lay)
;	(setq o_ctab (getvar "CTAB"))
;	(if (eq o_ctab "Model") (setq o_tile 0) (setq o_tile 1))
	(setq o_tile (getvar "TILEMODE") o_ctab (getvar "CTAB"))
	(entmake	(list (cons 0 "CIRCLE")
				(cons 100 "AcDbEntity")
				(cons 8 o_lay)
				(cons 100 "AcDbCircle")
				(cons 10 o_cen)
				(cons 40 o_rad)
			)
	)
)

;"|O|ELLIPSE"
(defun |O|ELLIPSE (o_cen o_maj o_ratio o_lay)
;	(setq o_ctab (getvar "CTAB"))
;	(if (eq o_ctab "Model") (setq o_tile 0) (setq o_tile 1))
	(setq o_tile (getvar "TILEMODE") o_ctab (getvar "CTAB"))
	(entmake	(list (cons 0 "ELLIPSE")
				(cons 100 "AcDbEntity")
				(cons 8 o_lay)
				(cons 100 "AcDbEllipse")
				(cons 10 o_cen)
				(cons 11 o_maj)
				(cons 40 o_ratio)
				(cons 41 0)
				(cons 42 (* 2 pi))
			)
	)
)

;"|O|LEADER"
(defun |O|LEADER (o_lpts o_tat o_lval o_pib o_lay)
	(setq o_ctab (getvar "CTAB"))
	(cond ((eq o_tat "T")
			(setq o_fl T o_73 0 o_off 213)
		)
		((eq o_tat "B")
			(setq o_bn (car o_lval) o_lval (cdr o_lval) o_fl T o_73 2 o_off 212)
		)
		(T (setq o_73 3 o_fl nil o_off nil))
	)
	(if (|N|ENTRE (|K|ANG (car o_lpts) (cadr o_lpts)) (list (/ PI 2) (* PI 1.5))) (setq o_ap 9 o_hdl '(1 0 0)) (setq o_ap 7 o_hdl '(-1 0 0)))
	(setq o_ds (getvar "DIMSTYLE") o_ts (getvar "DIMTXSTY") o_th (getvar "DIMTXT"))
	(if o_fl
		(progn
			(cond ((eq o_tat "T")
					(setq o_str "" o_strl 0 o_st+l "")
					(foreach o_val o_lval
						(setq o_str (strcat o_str o_val "\n") o_strl1 (strlen o_val))
						(if (> o_strl1 o_strl) (setq o_str+l o_val))
					)
					(|O|MTEXT o_pib (|T|BORRAU o_str) o_th o_ts o_lay 0 o_ap)
					(setq o_nat (entlast) o_enta (entget o_nat)
					      o_tbox (textbox (list (cons 1 o_str+l)))
					      o_41 (caadr o_tbox)
					)
				)
				((eq o_tat "B")
					(|B|INSERT o_bn o_pib o_lay 0 1 o_lval)
					(setq o_nat (entlast) o_entt (entget o_nat)
					      o_enta (append (list (car o_enta) (cadr o_enta) (cadddr o_enta) (caddr o_enta)) (cddddr o_enta))
					      o_41 0.0
					)
				)
			)
		)
		(setq o_enta nil o_nat nil o_41 0.0)
	)
	(entmake (append (list (cons 0 "LEADER")
				(cons 100 "AcDbEntity")
				(cons 3 o_ds)
				(cons 8 o_lay)
				(cons 100 "AcDbLeader")
				(cons 71 1)
				(cons 72 0)
				(cons 73 o_73)
				(cons 74 1)
				(cons 75 1)
				(cons 40 o_th)
		       		(cons 41 o_41)
				(cons 76 (length o_lpts))
				(cons 77 1)
				(cons 211 o_hdl)
			)
			(mapcar '(lambda (o_p) (cons 10 o_p)) o_lpts)
			(if o_off (list (cons o_off '(0.25 0.25 0))))
			(if o_nat (list (cons 340 o_nat)))
		)
	)
	(if o_enta
	  (progn
		(setq o_entl (entlast) o_apl (list (cons 102 "{ACAD_REACTORS") (cons 330 o_entl) (cons 102 "}"))
		      o_senta1 (|L|SUBL o_enta (|L|POS (assoc 330 o_enta) o_enta)) o_enta (|L|RESL o_enta (|L|POS (assoc 330 o_enta) o_enta))
		      o_enta (append o_senta1 o_apl o_enta)
		)
		(entmod o_enta)
	  )
	)
)

;"|O|LINE"
(defun |O|LINE (o_p1 o_p2 o_lay)
	(setq o_ctab (getvar "CTAB"))
;  	(if (eq o_ctab "Model") (setq o_tile 0) (setq o_tile 1))
;	(setq o_tile (getvar "TILEMODE") o_ctab (getvar "CTAB"))
	(entmake 	(list (cons 0 "LINE")
				(cons 100 "AcDbEntity")
				(cons 8 o_lay)
				(cons 100 "AcDbLine")
				(cons 10 o_p1)
				(cons 11 o_p2)
			)
	)
)

;"|O|LWPOLY"
(defun |O|LWPOLY (o_lpt o_lay o_c70)			;o_c70 = 0 polilinea abierta, 1 polilinea cerrada , 128 ltgen
;	(setq o_ctab (getvar "CTAB"))
; 	(if (eq o_ctab "Model") (setq o_tile 0) (setq o_tile 1))
	(entmake (append	(list (cons 0 "LWPOLYLINE")
					(cons 100 "AcDbEntity")
					(cons 8 o_lay)
					(cons 100 "AcDbPolyline")
					(cons 90 (length o_lpt))
					(cons 70 o_c70)
				)
				(mapcar '(lambda (o_p) (cons 10 o_p)) o_lpt)
			)
	)
)

;"|O|3DPOLY"
(defun |O|3DPOLY (o_lpt o_lay)			;o_c70 = 0 polilinea abierta, 1 polilinea cerrada , 128 ltgen
	(defun |O|VERTEX (o_lpts)
		(cond
			((null o_lpts) nil)
			(T
				(setq o_p (car o_lpts))
				(entmake (list (cons 0 "VERTEX")
						(cons 10 o_p)
						(cons 70 32)
					)
				)
				(|O|VERTEX (cdr o_lpts))
			)
		)
	)
;	(setq o_ctab (getvar "CTAB"))
; 	(if (eq o_ctab "Model") (setq o_tile 0) (setq o_tile 1))
	(entmake (list (cons 0 "POLYLINE")
			(cons 8 o_lay)
			(cons 100 "AcDb3dPolyline")
			(cons 66 1)
			(cons 70 8)
			(cons 75 0)
			(cons 210 '(0 0 1))
		)
	)
	(|O|VERTEX o_lpt)
	(entmake (list (cons 0 "SEQEND") (cons 8 o_lay)))
)

;"|O|CNIVEL"
(defun |O|CNIVEL (o_lpt o_lay o_c70 o_elev)			;o_c70 = 0 polilinea abierta, 1 polilinea cerrada
;	(setq o_ctab (getvar "CTAB"))
;  	(if (eq o_ctab "Model") (setq o_tile 0) (setq o_tile 1))
	(if (> (length o_lpt) 1)
		(entmake (append	(list (cons 0 "LWPOLYLINE")
						(cons 100 "AcDbEntity")
						(cons 8 o_lay)
						(cons 100 "AcDbPolyline")
						(cons 90 (length o_lpt))
						(cons 70 o_c70)
						(cons 38 o_elev)
						(cons 60 0)
					)
					(mapcar '(lambda (o_p) (cons 10 o_p)) o_lpt)
				)
		)
	)
)

;"|O|CNIVELS"
(defun |O|CNIVELS (o_lpt o_lay o_70 o_elev) ;o_c70 = 0 polilinea abierta, 1 polilinea cerrada
	(defun |O|CREAKN ()
		(setq o_lkn '() o_ckn 1.0 )
		(repeat o_nr
			(setq o_lkn (cons (cons 40 0.0) o_lkn))
		)
		(repeat (- (length o_lpt) o_nr)
			(setq o_lkn (cons (cons 40 o_ckn) o_lkn) o_ckn (+ o_ckn 1.0))
		)
		(repeat 4
			(setq o_lkn (cons (cons 40 o_ckn) o_lkn))
		)
		(reverse o_lkn)
	)
;	(setq o_ctab (getvar "CTAB"))
;  	(if (eq o_ctab "Model") (setq o_tile 0) (setq o_tile 1))
	(if (= o_70 1) (setq o_c70 11 o_nr 4) (setq o_c70 8 o_nr 4))
	(setq o_knots (+ (length o_lpt) 4))
	(if (> (length o_lpt) 1)
		(entmake (append	(list (cons 0 "SPLINE")
						(cons 100 "AcDbEntity")
						(cons 8 o_lay)
						(cons 100 "AcDbSpline")
						(cons 70 o_c70)
						(cons 71 3)
						(cons 72 (+ (length o_lpt) 4))
						(cons 73 (length o_lpt))
						(cons 74 0)
						(cons 60 0)
					)
					(|O|CREAKN)
					(mapcar '(lambda (o_p) (cons 10 (|K|Z+ (|K|XY o_p) o_elev))) o_lpt)
;;;					(mapcar '(lambda (o_p) (cons 11 (|K|Z+ (|K|XY o_p) o_elev))) o_lpt)
			)
		)
	)
)

;"|O|MTEXT"
(defun |O|MTEXT (o_pt o_texto o_alt o_sty o_lay o_w o_ap)
;	(setq o_ctab (getvar "CTAB"))
;  	(if (eq o_ctab "Model") (setq o_tile 0) (setq o_tile 1))
	(entmake	(list (cons 0 "MTEXT")         
				(cons 100 "AcDbEntity")
				(cons 8 o_lay)
				(cons 100 "AcDbMText")
				(cons 10 o_pt)
				(cons 40 o_alt)
				(cons 41 o_w)
			    	(cons 71 o_ap)
				(cons 1 o_texto)
				(cons 7 o_sty)
				(cons 73 2)
			)
	)
)

;"|O|POINT"
(defun |O|POINT (o_pt o_ang o_lay)
;	(setq o_ctab (getvar "CTAB"))
;  	(if (eq o_ctab "Model") (setq o_tile 0) (setq o_tile 1))
	(entmake	(list (cons 0 "POINT")
				(cons 100 "AcDbEntity")
				(cons 8 o_lay)
				(cons 100 "AcDbPoint")
				(cons 10 o_pt)
				(cons 50 o_ang)
			)
	)
)

;"|O|TEXT"	 pi1  pi2   altura Texto angulo ancho incl. estilo mirror 
(defun |O|TEXT (o_pt o_pt2 o_alt o_Texto o_ang o_wdt o_oa o_sty o_tgf o_jh o_jv o_lay)
;	(setq o_ctab (getvar "CTAB"))
;  	(if (eq o_ctab "Model") (setq o_tile 0) (setq o_tile 1))
	(entmake	(list (cons 0 "TEXT")
				(cons 100 "AcDbEntity")
				(cons 8 o_lay)
				(cons 100 "AcDbText")
				(cons 10 o_pt)
				(cons 40 o_alt)
				(cons 50 o_ang)
				(cons 41 o_wdt)
				(cons 51 o_oa)
				(cons 7 o_sty)
				(cons 71 o_tgf)
				(cons 72 o_jh)
				(cons 11 o_pt2)
				(cons 100 "AcDbText")
				(cons 1 o_texto)
				(cons 73 o_jv)
			)
	)
)

;"|O|DELENTS"
(defun |O|DELENTS (o_lent)
	(cond
		((null o_lent) nil)
		(t
			(entdel (car o_lent))
			(|O|DELENTS (cdr o_lent))
		)
	)
)

;"|O|ESPIRAL"
(defun |O|ESPIRAL (o_pc1 o_pc2 o_pc3 o_t1 o_t2 o_lay)
	(entmake	(list (cons 0 "SPLINE")
				(cons 100 "AcDbEntity")
				(cons 8 o_lay)
				(cons 100 "AcDbSpline")
				(cons 210 (list 0.0 0.0 1.0))
				(cons 70 8)
				(cons 71 3)
				(cons 73 5)
				(cons 74 3)
				(cons 10 o_pc1)
				(cons 10 o_pc2)
				(cons 10 o_pc3)
				(cons 10 o_t1)
				(cons 10 o_t2)
				(cons 11 o_pc1)
				(cons 11 o_pc2)
				(cons 11 o_pc3)
			)
	)
)



;crear una xref
;"|O|XREF"
(defun |O|XREF (o_path o_xrname o_pto o_lay)
	(if (not (|O|BUSCAR "Block" o_xrname))
		(progn
			(setq o_70 36)
			(entmake	(list	(cons 0 "BLOCK")
						(cons 100 "AcDbEntity")
						(cons 8 o_lay)
						(cons 100 "AcDbBlockBegin")
						(cons 2 o_xrname)
						(cons 10 o_pto)
						(cons 3 o_xrname)
						(cons 1 o_path)
						(cons 70 o_70)
					)
			)
			(entmake	(list	(cons 0 "ENDBLK")
						(cons 100 "AcDbEntity")
						(cons 100 "AcDbBlockEnd")
					)
			)
		)
		(princ "\n la xref ya existe")
	)
	(entmake	(list	(cons 0 "INSERT")
				(cons 100 "AcDbEntity")
				(cons 8 o_lay)
				(cons 100 "AcDbBlockReference")
				(cons 2 o_xrname)
				(cons 10 o_pto)
				(cons 41 1)
				(cons 42 1)
				(cons 43 1)
				(cons 50 0)
			)
	)
)

;"|O|ACTE"
(defun |O|ACTLWP (o_ent o_lpts)
	(cond
		((null o_lpts) o_ent)
		((= (caar o_ent) 10)
			(cons (cons 10 (car o_lpts)) (|O|ACTLWP (cdr o_ent) (cdr o_lpts)))
		)
		(T
			(cons (car o_ent) (|O|ACTLWP (cdr o_ent) o_lpts))
		)
	)
)

;"|O|SCAL"
(defun |O|SCAL ()
	(defun |O|ESCPL (o_lpts o_sc o_pa)
		(cond
			((null o_lpts) nil)
			((null o_pa) (cons (car o_lpts) (|O|ESCPL (cdr o_lpts) o_sc (car o_lpts))))
			(T
				(setq o_pt (car o_lpts) o_di (|K|DISTH o_pa o_pt) o_ab (|K|ANG o_pa o_pt)
				      o_pd (|K|POLAR o_pa o_ab (* o_di o_sc)) o_di (|K|DISTH o_pt o_pd)
				      o_lpts (|FV|TRASLADAR o_lpts o_pd)
				)
				(cons o_pd (|O|ESCPL (cdr o_lpts) o_sc o_pd))
			)
		)
	)
	(defun |O|ESC (o_sc o_lobjs)
		(cond
			((null o_lobjs) nil)
			((null o_sc) nil)
			(T
				(setq o_obj (entget (car o_lobjs)) o_tip (|O|ITEM 0 o_obj))
				(cond
					((eq o_tip "INSERT")
						(|B|ESC (car o_lobjs) o_sc)
					)
					((or (eq o_tip "TEXT") (eq o_tip "MTEXT") (eq o_tip "CIRCLE") (eq o_tip "ARC"))
						(setq o_ats (|O|ITEM 40 o_obj) o_obj (|O|REEMP 40 (* o_sc o_ats) o_obj))
						(entmod o_obj)
					)
					((eq o_tip "LINE")
						(|FV|ESTIRAR (list (|O|ITEM 10 o_obj) (|O|ITEM 11 o_obj)) o_sc o_sc)
					)
					((eq o_tip "LWPOLYLINE")
						(entmod (|O|ACTLWP o_obj (|O|ESCPL (|A|LVPOLI (car o_lobjs)) o_sc nil)))
					)
					(T (setq o_pin (|O|ITEM 10 o_obj))
						(command "SCALE" (car o_lobjs) "" o_pin o_sc)
					)
				)
				(|O|ESC o_sc (cdr o_lobjs))
			)
		)
	)
	(|G|SET0VAR)
	(setq o_sc (getreal "\nFactor de escala: "))
	(prompt "\nseleccione los objetos a escalar, ")
	(|O|ESC o_sc (|L|SSL (ssget)))
	(|G|RESTVAR T)
)

;"|O|ROTAR"
(defun |O|ROTAR ()
	(defun |O|ROTPL (o_an o_lpts o_po)
		(cond
			((null o_lpts) nil)
			((null o_po) (cons (car o_lpts) (|O|ROTPL o_an (cdr o_lpts) (car o_lpts))))
			(T
				(setq o_pt (car o_lpts) o_di (|K|DISTH o_po o_pt) o_ab (|K|ANG o_po o_pt)
				      o_pd (|K|POLAR o_po (+ o_ab o_an) o_di)
				)
				(cons o_pd (|O|ROTPL o_an (cdr o_lpts) o_po))
			)
		)
	)
	
	(defun |O|ROT (o_an o_lobjs)
		(cond
			((null o_lobjs) nil)
			((null o_an) (|O|ROT PI o_lobjs))
			(T
				(setq o_obj (entget (car o_lobjs)) o_tip (|O|ITEM 0 o_obj))
				(cond
					((eq o_tip "INSERT")
						(|B|ROTAR (car o_lobjs) o_an)
					)
					((or (eq o_tip "TEXT") (eq o_tip "MTEXT"))
						(setq o_ats (|O|ITEM 50 o_obj) o_obj (|O|REEMP 50 (+ o_an o_ats) o_obj))
						(entmod o_obj)
					)
					((eq o_tip "ARC")
						(setq o_ai (|O|ITEM 50 o_obj) o_af (|O|ITEM 51 o_obj)
						      o_obj (|O|REEMP 50 (+ o_an o_ats) o_obj)
						      o_obj (|O|REEMP 51 (+ o_an o_ats) o_obj)
						)
						(entmod o_obj)
					)
					((eq o_tip "LINE")
						(setq o_p1 (|O|ITEM 10 o_obj) o_p2 (cdr assoc 11 o_obj)
						      o_obj (|O|REEMP 11 (|K|POLAR o_p1 (+ (|K|ANG o_p1 o_p2) o_an) (|K|DIST o_p1 o_p2)) o_obj)
						)
						(entmod o_obj)
					)
					((eq o_tip "LWPOLYLINE")
						(entmod (|O|ACTLWP o_obj (|O|ROTPL o_an (|A|LVPOLI (car o_lobjs)) nil)))
					)
					(T (setq o_pin (|O|ITEM 10 o_obj))
						(command "ROTATE" (car o_lobjs) "" o_pin o_an)
					)
				)
				(|O|ROT o_an (cdr o_lobjs))
			)
		)
	)
	(|G|SET0VAR)
	(prompt "\nseleccione los objetos a rotar, ")
	(|O|ROT (|N|GAR (getreal "\nángulo:? ")) (|L|SSL (ssget)))
	(|G|RESTVAR T)
)
